module intri-date {

  namespace "intri:intri-date";
  prefix "intri-date";
  organization "
    Intrising Inc.";
  contact "
    intrising@intrising.com.tw";
  revision 2022-06-24 {
    description "Build date.";
  }

  grouping Date {
    leaf Year {
      mandatory "true";
      type int32;
    }
    leaf Month {
      mandatory "true";
      type int32;
    }
    leaf Day {
      mandatory "true";
      type int32;
    }
  }
}
