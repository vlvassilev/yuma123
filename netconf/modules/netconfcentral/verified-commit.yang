module verified-commit {

    namespace "file:///draft-cole-netconf-robust-config-01.txt";

    prefix "vc";

    organization  "IETF";

    contact "[add contact info here].";

    description 
      "NETCONF verified commit procedure.";

    revision 2009-06-09 {
        description  "Initial version.";
    }

    rpc start-verified-commit {
        description
          "The verified commit procedure is started by
           invoking this operation.  The NETCONF procedure
           for the :confirmed-commit capability is followed,
           with the additional semantics:
 
             * the server will cancel the verified-commit
               procedure if the <cancel-verified-commit>
               operation is invoked.

             * the server will start, monitor, and report
               the verification test(s) during the time
               interval after this operation, and before
               the 'timeout' interval has expired.

             * the server will complete the verified commit
               procedure if the <complete-verified-commit>
               operation is invoked before the timeout interval
               has expired.

             * the server will generate the <verifiedCommitStatus>
               notification for each verification test specified
               in the 'test-template leaf-list, indicating the
               result of each verification test.

             * the server will generate the <verifiedCommitComplete>
               notification at the completion of the entire
               verified commit procedure, indicating the
               final verified commit proceudure status.
          ";

        input {
            leaf timeout {
                description
                  "The time interval the server must wait before
                   reverting the <running> configuration
                   and automatically canceling the verified
                   commit procedure.  (Note that the verified
                   commit procedure will also be automatically
                   canceled if the session that invokes this operation
                   is terminated for any reason.";
                type uint32;
                units seconds;
                default 600;
            }

            leaf-list test-template {
                description
                  "Identifies a verification test control entry
                   for the server to use for the verification
                   portion of the verified commit procedure.

                   The verification test control entry must conform
                   to the requirements specified in section X.X,
                   and the server must be capable of starting,
                   monitoring, and reporting the results of
                   the verification test, as required.

                   The server will also generate the <verifiedCommitStatus>
                   notification, as specified for the verification
                   test control entry indicated by this parameter.";
                type instance-identifier;
                min-elements 1;
            }
        }
    }



    rpc cancel-verified-commit {
        description
          "Cancel a verified commit procedure already in progress.

           If no verified commit procedure is currently in
           progress, then an 'operation-failed' error is
           generated, and the value 'no-verified-commit'
           is used for the error-app-tag field.

           If the verified commit procedure in progress
           cannot be canceled for any reason, then an
           'operation-failed' error is returned, and
           the value 'cancel-failed' is used in the
           error-app-tag field.

           If any verification tests associated with this
           verified commit procedure are still in progress,
           they will be canceled by this operation.

           If the verified commit procedure in progress
           is canceled, then the server will return <ok/>.
          ";
    }

    rpc complete-verified-commit {
        description
          "Complete a verified commit procedure already in progress.

           If no verified commit procedure is currently in
           progress, then an 'operation-failed' error is
           generated, and the value 'no-verified-commit'
           is used for the error-app-tag field.

           If the verified commit procedure in progress
           cannot be completed for any reason, then an
           'operation-failed' error is returned, and
           the value 'complete-failed' is used in the
           error-app-tag field.

           If any verification tests associated with this
           verified commit procedure are still in progress,
           they will be canceled by this operation.

           If the verified commit procedure in progress
           is completed, then the server will return <ok/>.
          ";
    }

    notification verifiedCommitStatus {
        description
          "Contains the current of final status of
           a verification test being invoked on behalf
           of the current verified commit procedure.";

        leaf testIdentifier {
            description
              "Indicates which verification test this
               status report is associated with.
               This value will identify the same node
               as specified in a 'test-template'
               parameter instance provided in the
               <start-verified-commit> operation.";
            type instance-identifier;
            mandatory true;
        }

        leaf statusType {
            description
              "Indicates the type of status report that
               this notification contains.";
            type enumeration {
                enum partial {
                    description
                      "Indicates this is a partial status result
                       and the verification test is still in 
                       progress.";
                }
                enum final {
                    description
                      "Indicates this is the final status result
                       and the verification test is completed
                       or canceled.";
                }
            }
            mandatory true;
        }

        leaf status {
            description
              "Indicates the NETCONF error-tag value most
               closely associated with the test status.
               The string 'ok' is used to indicate that
               no errors have been detected.";
            type string;
            reference "RFC 4741bis, Appendix A";
            mandatory true;
        }

        anyxml extendedStatus {
            description
              "Indicates test-specific status data.
               The requirements for verification tests
               (section X.X) describes how the semantics
               of this structure are determined.";
        }
    }

    notification verifiedCommitComplete {
        description
          "Contains the final status of the
           current verified commit procedure.";

        leaf status {
            description
              "Indicates the NETCONF error-tag value most
               closely associated with the test status.
               The string 'ok' is used to indicate that
               no errors have been detected.";
            type string;
            reference "RFC 4741bis, Appendix A";
            mandatory true;
        }
    }
            
}
