module intri-stp {
  namespace "intri:intri-stp";
  prefix "intri-stp";
  import stppb {
    prefix "stppb";
  }
  organization "Intrising Inc.";
  contact "xxx@intrising.com.tw";
  revision 2022-06-14 {
    description "Build date.";
  }
}
