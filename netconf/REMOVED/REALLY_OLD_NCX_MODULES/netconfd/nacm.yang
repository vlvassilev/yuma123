module nacm {

    namespace "http://netconfcentral.com/ns/nacm";

    prefix "nacm";

    import ncx { prefix ncx; }

    import ncxtypes { prefix nt; }

    import xsd { prefix xs; }

    import nctypes { prefix nct; }

    import yang-types { prefix yt; }

    organization  "Netconf Central";

    contact "Andy Bierman <support@netconfcentral.com>.";

    description 
      "NETCONF Agent Access Control Model Parameters";


    // Global Security Level

    typedef NcxAccessControlMode {
      description 
        "NCX System access control mode.
          off == no access control checking enforced 
          warn == warn only if access violation detected
          loose == any RPC method in the netconf namespace can
              be invoked;  read-only data allowed for all
          strict == ncxacl RPC entry must be present to invoke
              an RPC method; ncxacl Data entry must be present
              to access any data. (Except for user == 'root'.)
         ";
      type enumeration {
        enum off;
	enum warn;
        enum loose;
	enum strict;
      }
    }

    // Administrative Roles

    typedef NcxAccessAdminRole {
      description 
        "Type of administrative role assigned to the session
         root == root account, no access control applied
         admin == administrative account, access control applied
         guest == guest account, read-only and configured
                   access control applied.";
      type enumeration {
        enum root;
	enum admin;
	enum guest;
      }
    }

    // Access Denied Event Request Type

    typedef NcxAccessRequestType {
      description
       "Type of request causing an access violation.
          rpcRequest:
            An RPC method invocation request was denied.
          dataRead:
            A configuration data read request was denied.
          dataWrite:
            A configuration data write request was denied.";
      type enumeration {
        enum rpcRequest;
	enum dataRead;
	enum dataWrite;
      }
    }

    // NCX Access Name

    typedef NcxAccessName {
      description "NCX Access Name string.";
      type nt:NcxName;
    }

    // Group Name List

    typedef NcxAccessNameList {
      description 
        "List of NcxAcessName strings.";
      type string;
      ncx:xsdlist "nt:NcxAccessName";
      ncx:no-duplicates;
    }

    // RPC Type

    typedef NcxAccessRpcType {
      description "NCX RPC Type Classifications";
      type enumeration {
        enum other;
	enum config;
	enum exec;
	enum monitor;
	enum debug;
      }
    }

    // RPC Type List

    typedef NcxAccessRpcTypeList {
      description "List NCX RPC Type Classifications";
      type string;
      ncx:xsdlist "nt:NcxAccessRpcType";
      ncx:no-duplicates;
      ncx:merge-type sort;
    }

    // Access Permission Type

    typedef NcxAccessType {
      description 
        "NETCONF Data Access Types:

          none == no access allowed at all.
               This value is used in ACLs, not max-access clauses.
          read-only == read access allowed in all operations.
               This value implies notify access as well.
          read-write == all but create/delete allowed.
               Values can be read and edited.
               Merge and replace operations will be permitted, even
               (e.g., create the instance if it does not exist.
               This allows a manager to save static or agent-created entries
               in copy-config operations, and then reload them later.
          read-create == all access allowed
               Instances can be read, created, edited, and deleted.";
      type enumeration
        enum none;
	enum read-only;
	enum read-write;
	enum read-create;
      }
      default "none";
    }

    // Access Control Rule Type

    typedef NcxAccessRuleType {
      description 
        "NCX Access Control Rule Type";
      type enumeration { 
        enum permit;
	enum deny;
      }
    }

    // Grouping to identify XML nodes to associate with an 
    // access control rule

    grouping NcxAccessNodeList {
      description 
        "NCX Access Control Node Identifier Type";

      container { 
        leaf namespaceUri {
           type xsd:anyURI;
        }
        leaf-list elementNames { 
	  type NcxAccessName;
        }
      }
    }

    # Grouping to represent the accessDeniedEvent contents

    grouping NcxAccessDeniedEvent {
      description
         "Access Denied Event Notification Contents";

      container {
        config false;

          leaf eventClass {
             type string;
          }

          leaf eventSeverity {
             type string;
          }
          leaf eventTime {
            type yt:date-and-time;
          }
          leaf eventSessionId {
            type uint32;
          }
          leaf eventSessionAddress {
            type yt:ip-address;
          }
          leaf eventGroupName {
            type NcxAccessName;
          }
          leaf eventAccessRequested {
            type NcxAccessRequestType;
          } 
          leaf eventErrorPath {
            type string;
          }
        }
      }
    }


    // Grouping to indicate access control configuration 
    // capabilities supported by the agent

    typedef NcxAccessConfigCapabilities {
      description
         "Read-only parameters indicating some agent access control
          capabilities.";
      type bits {
        bit globalConfig;
        bit groupConfig;
        bit rpcAccessConfig;
        bit rpcTypeAccessConfig;
        bit databaseAccessConfig;
        bit notificationAccessConfig;
      }
    }

    // Global Config Profile

    grouping NcxAccessGlobalProfile {
      description
         "Read-write parameters controlling some global 
          agent access control behavior.";
      container {
        leaf accessControlMode {
          type NcxAccessControlMode;
        }
        leaf accessDeniedEventEnabled {
          type boolean;
          default true;
        }
      }
    }

    // One Group Record
    // Membership by user name or host address

    grouping NcxAccessGroupRec {
      description 
        "One NCX Group Membership Record
         The 'role' parameter should not be changed
         after it is set.

         If a user name is present in the 'users' table then it
         is a member of the group identified by 'name'.

         If a host address is present in the 'hosts' table then it
         is a member of the group identified by 'name'. 

         If both 'users' and 'hosts' are missing then the group
         will be considered empty.";

      container {
        leaf name {
          type NcxAccessName;
        }
        leaf role {
          type NcxAccessAdminRole;
        }
 
        container users {
          list user {
            key user;
            leaf user { type NcxAccessName; }
          }
        }

        container hosts {
          list host {
            key host;
            leaf host { type yt:ip-address; }
          }
        }
      }
    }

    // NCX Access Group Table

    type NcxAccessGroupTable {
      description 
        "NCX Group Membership Table
         Users and hosts can belong to any number of groups.
         The group name must be unique.";
      syntax {
        # scoped names can be local (child of one of the 
        # table members) or remote (just like SMI but scoped)
        xcontainer [group/name] {
          NcxAccessGroupRec group;
        }
      }
    }


    #
    # One RPC Method Access Control Rule
    #

    type NcxAccessRpcRule {
      description 
        "One NCX RPC Method Access Control Rule";
      syntax {
        container {
          uint32             ruleNumber;
          NcxAccessRuleType  ruleType;
          NcxAccessNameList groupList;
          choice rpcTarget {
            NcxAccessRpcTypeList rpcTypeList;
            NcxAccessNodeList  rpcMethodList;
            string             xpathExpr;
            empty               all;
          }
        }
      }
    }

    #
    # Table of RPC Method Rules
    #

    type NcxAccessRpcTable {
      description 
        "NCX Access Control Rules for RPC Methods.";
      syntax {
        xcontainer [rpcRule/ruleNumber] {
          NcxAccessRpcRule rpcRule;
        }
      }
    }

    #
    # One Data Access Control Rule
    #

    type NcxAccessDataRule {
      description 
        "One NCX Data Access Control Rule";
      syntax {
        container {
          uint32 ruleNumber;
          NcxAccessType access;
          NcxAccessNameList groupList;
          choice dataTarget {
            NcxAccessNodeList  dataNodeList;
            string             xpathExpr;
            empty               all;
          }
        }
      }
    }

    #
    # Table of Data Access Control Rules
    #

    type NcxAccessDataTable {
      description 
        "NCX Access Control Rules for Configuration Data";
      syntax {
        xcontainer [dataRule/ruleNumber] {
          NcxAccessDataRule dataRule;
        }
      }
    }

    #
    # One Notification Access Control Rule
    #

    type NcxAccessNotificationRule {
      description 
        "One NCX Notification Access Control Rule";
      syntax {
        container {
          uint32 ruleNumber;
          NcxAccessRuleType ruleType;
          NcxAccessNameList groupList;
          choice eventTarget {
            NcxAccessNodeList  eventNodeList;
            string             xpathExpr;
            empty              all;
          }
        }
      }
    }

    #
    # Table of Notification Access Control Rules
    #

    type NcxAccessNotificationTable {
      description 
        "NCX Access Control Rules for Notifications.";
      syntax {
        xcontainer [notificationRule/ruleNumber] {
          NcxAccessNotificationRule notificationRule;
        }
      }
    }

    #
    # ****** Top Level Accessible Object *****
    # Parameter Set to Configure NCX Access Control
    #

    parmset accessControl {
      description
         "Parameters for NETCONF Access Control.";
      order loose;
      type data;

      parms {
        parm configCapabilities {
          description 
            "NCX ACM configuration supported by the agent";
          type NcxAccessConfigCapabilities;
          data-class state;
          usage mandatory;
        }

        parm profile {
          description "NCX Global Access Control Profile Parameters";
          type NcxAccessGlobalProfile;
          usage mandatory;
        }

        parm groups {
          description "NCX Group Membership Table";
          type NcxAccessGroupTable;
          usage mandatory;
        }

        parm rpcRules {
          description "NCX RPC Execution Access Control Table ";
          type NcxAccessRpcTable;
          usage optional;
        }

        parm dataRules {
          description "NCX Data Model Access Control Table ";
          type NcxAccessDataTable;
          usage optional;
        }

        parm notificationRules {
          description "NCX Data Model Access Control Table ";
          type NcxAccessNotificationTable;
          usage optional;
        }

      }
    }

  }
}
