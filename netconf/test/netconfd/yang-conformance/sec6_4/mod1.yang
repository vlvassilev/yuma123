module mod1 {
  prefix m1;
  namespace "http://yuma123.org/ns/sec6_4/mod1";

  container m1 {
    leaf foo {
      type uint32;
    }
    leaf bar {
      type uint32;
      must ". <= 0.75 * ../foo";
    }
  }
}
