submodule intri-acl-enum {
  belongs-to "intri-acl" {
    prefix "intri-acl-enum";
  }
  revision 2022-06-14 {
    description "Build date.";
  }
  // core/acl/common.proto
  typedef RuleActionTypeOptions {
    type enumeration {
      enum RULE_ACTION_TYPE_UNUSED {
        description "[Unused] this rule is unused yet";
        value 0;
      }
      enum RULE_ACTION_TYPE_PERMIT {
        description "[Permit] this rule action will permit packet";
        value 1;
      }
      enum RULE_ACTION_TYPE_DENY {
        description "[Deny] this rule action will deny packet";
        value 2;
      }
      enum RULE_ACTION_TYPE_MIRROR {
        description "*internal usage";
        value 3;
      }
    }
  }
  // core/acl/common.proto
  typedef RuleParamTypeOptions {
    type enumeration {
      enum RULE_PARAM_TYPE_MAC {
        description "[MAC] this rule param is MAC address specification";
        value 0;
      }
      enum RULE_PARAM_TYPE_IP_V_4 {
        description "[IPv4] this rule param is IPv4 address specification";
        value 1;
      }
      enum RULE_PARAM_TYPE_IP_V_6 {
        description "[IPv6] this rule param is IPv6 address specification";
        value 2;
      }
    }
  }
  // core/acl/common.proto
  typedef RuleDirectionTypeOptions {
    type enumeration {
      enum RULE_DIRECTION_TYPE_INGRESS {
        description "*internal usage";
        value 0;
      }
      enum RULE_DIRECTION_TYPE_EGRESS {
        description "*internal usage";
        value 1;
      }
    }
  }
}
