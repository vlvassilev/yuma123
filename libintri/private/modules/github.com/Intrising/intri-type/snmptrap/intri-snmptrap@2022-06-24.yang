module intri-snmptrap {

  namespace "intri:intri-snmptrap";
  prefix "intri-snmptrap";
  organization "
    Intrising Inc.";
  contact "
    intrising@intrising.com.tw";
  revision 2022-06-24 {
    description "Build date.";
  }

  grouping SNMPTrapCounter {
    leaf ErrorCounts {
      mandatory "true";
      type int32;
    }
    leaf TrapCounts {
      mandatory "true";
      type int32;
    }
  }
}
