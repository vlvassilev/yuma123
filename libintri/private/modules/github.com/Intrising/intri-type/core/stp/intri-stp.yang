// Code generated by protoc-gen-yang. DO NOT EDIT.


/* ****************************************************************************************************
 * Import Path : "github.com/Intrising/intri-type/core/stp"                                           *
 * Dir Path    : github.com/Intrising/intri-type/core/stp                                             *
 * Go Package  : stp                                                                                  *
 * Files       : 2                                                                                    *
 **************************************************************************************************** */
module intri-stp {

  namespace "intri:intri-stp";

  prefix "intri-stp";

  organization "Intrising Inc.";

  contact "intrising@intrising.com.tw";

  revision 2022-06-23 {
    description "Build date.";
  }

  import intri-empty {
    prefix intri-empty;
  }
  import intri-device {
    prefix intri-device;
  }


  /* **************************************************************************************************
   * Enums       : 5                                                                                  *
   ************************************************************************************************** */
  /* core/stp/stp.proto */
  typedef BridgeConfigModeTypeOptions {
    type enumeration {
      enum BRIDGE_CONFIG_MODE_TYPE_DISABLED {
        description "[Disabled] Disabled mode";
        value 0;
      }
      enum BRIDGE_CONFIG_MODE_TYPE_STP {
        description "[STP] Stp bridge mode";
        value 1;
      }
      enum BRIDGE_CONFIG_MODE_TYPE_RSTP {
        description "[RSTP] Rstp bridge mode";
        value 2;
      }
      enum BRIDGE_CONFIG_MODE_TYPE_MSTP {
        description "[MSTP] Mstp bridge mode";
        value 3;
      }
    }
  }
  /* core/stp/stp.proto */
  typedef PortConfigAdminP2PPortTypeOptions {
    type enumeration {
      enum PORT_CONFIG_ADMIN_P2P_PORT_TYPE_AUTO {
        description "[Auto] Auto mode";
        value 0;
      }
      enum PORT_CONFIG_ADMIN_P2P_PORT_TYPE_FORCE_FALSE {
        description "[Force False] Force false mode";
        value 1;
      }
      enum PORT_CONFIG_ADMIN_P2P_PORT_TYPE_FORCE_TRUE {
        description "[Force True] Force true mode";
        value 2;
      }
    }
  }
  /* core/stp/stp.proto */
  typedef PortConfigBPDUGuardTypeOptions {
    type enumeration {
      enum PORT_CONFIG_BPDU_GUARD_TYPE_DISABLED {
        description "[Disabled] Disabled mode";
        value 0;
      }
      enum PORT_CONFIG_BPDU_GUARD_TYPE_DROP_AND_EVENT {
        description "[Drop And Event] Drop and event mode";
        value 1;
      }
      enum PORT_CONFIG_BPDU_GUARD_TYPE_BLOCK_PORT {
        description "[Block Port] Block port mode";
        value 2;
      }
    }
  }
  /* core/stp/stp.proto */
  typedef PortStatusStateTypeOptions {
    type enumeration {
      enum PORT_STATUS_STATE_TYPE_UNKNOWN {
        description "[Unknown] Unknown state";
        value 0;
      }
      enum PORT_STATUS_STATE_TYPE_DISCARDING {
        description "[Discarding] Discarding state";
        value 1;
      }
      enum PORT_STATUS_STATE_TYPE_LEARNING {
        description "[Learning] Learning state ";
        value 2;
      }
      enum PORT_STATUS_STATE_TYPE_FORWARDING {
        description "[Forwarding] Forwarding state";
        value 3;
      }
      enum PORT_STATUS_STATE_TYPE_BLOCKING {
        description "[Blocking] Blocking state";
        value 4;
      }
      enum PORT_STATUS_STATE_TYPE_LISTENING {
        description "[Listening] Listening state";
        value 5;
      }
      enum PORT_STATUS_STATE_TYPE_BROKEN {
        description "[Broken] Broken state";
        value 6;
      }
    }
  }
  /* core/stp/stp.proto */
  typedef PortStatusRoleTypeOptions {
    type enumeration {
      enum PORT_STATUS_ROLE_TYPE_UNKNOWN {
        description "[Unknown] Unknown";
        value 0;
      }
      enum PORT_STATUS_ROLE_TYPE_ROOT {
        description "[Root bridge] Root bridge";
        value 1;
      }
      enum PORT_STATUS_ROLE_TYPE_DESIGNATED {
        description "[Designated bridge] Designated bridge";
        value 2;
      }
      enum PORT_STATUS_ROLE_TYPE_ALTERNATE {
        description "[Alternate bridge] Alternate bridge";
        value 3;
      }
      enum PORT_STATUS_ROLE_TYPE_BACKUP {
        description "[Backup bridge] Backup bridge";
        value 4;
      }
      enum PORT_STATUS_ROLE_TYPE_MASTER {
        description "[Master bridge] Master bridge";
        value 5;
      }
      enum PORT_STATUS_ROLE_TYPE_DISABLED {
        description "[Disabled] Disabled";
        value 6;
      }
    }
  }


  /* **************************************************************************************************
   * Msgs        : 56                                                                                 *
   ************************************************************************************************** */
  /* core/stp/stp.proto */
  grouping MSTPConfig {
    leaf Mode {
      type BridgeConfigModeTypeOptions;
    }
    leaf Name {
      type string;
    }
    leaf Revision {
      type int32;
    }
    leaf MaxAge {
      type int32;
    }
    leaf HelloTime {
      type int32;
    }
    leaf ForwardDelay {
      type int32;
    }
    leaf MaxHops {
      type int32;
    }
    leaf TxHoldCount {
      type int32;
    }
    container Cist {
      uses CISTEntry;
    }
    container Mstis {
      list Mstis_Entry {
        uses MSTIEntry;
      }
    }
  }
  /* core/stp/stp.proto */
  grouping CISTEntry {
    leaf No {
      type int32;
    }
    leaf Priority {
      type int32;
    }
    container Ports {
      list Ports_Entry {
        uses MSTPCistPort;
      }
    }
  }
  /* core/stp/stp.proto */
  grouping MSTIEntry {
    leaf No {
      type int32;
    }
    container Vlans {
      leaf-list Vlans_Entry {
        type int32;
      }
    }
    leaf Enabled {
      type boolean;
    }
    leaf Priority {
      type int32;
    }
    container Ports {
      list Ports_Entry {
        uses MSTPMstiPort;
      }
    }
  }
  /* core/stp/stp.proto */
  grouping MSTIList {
    container List {
      list List_Entry {
        uses MSTIEntry;
      }
    }
  }
  /* core/stp/stp.proto */
  grouping MSTPCistPort {
    leaf No {
      type int32;
    }
    leaf PathCost {
      type int32;
    }
    leaf Priority {
      type int32;
    }
    leaf STPEnabled {
      type boolean;
    }
    leaf P2PMode {
      type PortConfigAdminP2PPortTypeOptions;
    }
    leaf EdgeMode {
      type boolean;
    }
    leaf BPDUGuard {
      type PortConfigBPDUGuardTypeOptions;
    }
    leaf RestrictRoot {
      type boolean;
    }
  }
  /* core/stp/stp.proto */
  grouping MSTPMstiPort {
    leaf No {
      type int32;
    }
    leaf PathCost {
      type int32;
    }
    leaf Priority {
      type int32;
    }
  }
  /* core/stp/stp.proto */
  grouping MSTPID {
    leaf MACAddress {
      type string;
    }
    leaf Priority {
      type int32;
    }
  }
  /* core/stp/stp.proto */
  grouping CISTStatus {
    leaf No {
      type int32;
    }
    container BridgeID {
      uses MSTPID;
    }
    container RootID {
      uses MSTPID;
    }
    leaf RootPort {
      type int32;
    }
    leaf RootCost {
      type int32;
    }
    container RegionalRoot {
      uses MSTPID;
    }
    leaf InternalRootCost {
      type int32;
    }
    leaf TopologyChange {
      type boolean;
    }
    leaf TopologyChangeCount {
      type int32;
    }
    leaf TimeSinceTopologyChange {
      type int32;
    }
    container Ports {
      list Ports_Entry {
        uses CISTPortEntryStatus;
      }
    }
  }
  /* core/stp/stp.proto */
  grouping CISTPortEntryStatus {
    leaf No {
      type int32;
    }
    leaf Role {
      type string;
    }
    leaf State {
      type string;
    }
    leaf Priority {
      type int32;
    }
    leaf PathCost {
      type int32;
    }
    leaf EdgeMode {
      type boolean;
    }
    leaf P2PMode {
      type boolean;
    }
    leaf Uptime {
      type int32;
    }
    leaf BPDUGuard {
      type string;
    }
  }
  /* core/stp/stp.proto */
  grouping MSTIStatus {
    container List {
      list List_Entry {
        uses MSTIStatusEntry;
      }
    }
  }
  /* core/stp/stp.proto */
  grouping MSTIStatusEntry {
    leaf No {
      type int32;
    }
    container BridgeID {
      uses MSTPID;
    }
    container RootID {
      uses MSTPID;
    }
    leaf RootPort {
      type int32;
    }
    leaf RootCost {
      type int32;
    }
    leaf TopologyChange {
      type boolean;
    }
    leaf TopologyChangeCount {
      type int32;
    }
    leaf TimeSinceTopologyChange {
      type int32;
    }
    container Ports {
      list Ports_Entry {
        uses MSTIPortStatusEntry;
      }
    }
  }
  /* core/stp/stp.proto */
  grouping MSTIPortStatusEntry {
    leaf No {
      type int32;
    }
    leaf Role {
      type string;
    }
    leaf State {
      type string;
    }
    leaf Priority {
      type int32;
    }
    leaf PathCost {
      type int32;
    }
    leaf Uptime {
      type int32;
    }
  }
  /* core/stp/stp.proto */
  grouping MSTPVLANGroupPortEntry {
    leaf PortNo {
      type int32;
    }
    leaf Tagged {
      type boolean;
    }
  }
  /* core/stp/stp.proto */
  grouping MSTPVLANGroupEntry {
    leaf VLANID {
      type int32;
    }
    container Ports {
      list Ports_Entry {
        uses MSTPVLANGroupPortEntry;
      }
    }
  }
  /* core/stp/stp.proto */
  grouping STPConfigBridge {
    leaf Mode {
      type BridgeConfigModeTypeOptions;
    }
    leaf Priority {
      type int32;
    }
    leaf HelloTime {
      type int32;
    }
    leaf MaxAge {
      type int32;
    }
    leaf ForwardDelay {
      type int32;
    }
    leaf TxHoldCount {
      type int32;
    }
    leaf MSTPRegionName {
      type string;
    }
    leaf MSTPRevisionLevel {
      type int32;
    }
    leaf MSTPMaxHops {
      type int32;
    }
  }
  /* core/stp/stp.proto */
  grouping STPConfigPortEntry {
    leaf PortNo {
      type int32;
    }
    leaf Enabled {
      type boolean;
    }
    leaf Priority {
      type int32;
    }
    leaf AdminP2PPort {
      type PortConfigAdminP2PPortTypeOptions;
    }
    leaf AdminEdgePort {
      type boolean;
    }
    leaf AdminPathCost {
      type int32;
    }
    leaf MSTPDefaultPriority {
      type int32;
    }
    container MSTPPortPriority {
      leaf-list MSTPPortPriority_Entry {
        type string;
      }
    }
    leaf MSTPDefaultAdminPathCost {
      type int32;
    }
    container MSTPPortAdminPathCost {
      leaf-list MSTPPortAdminPathCost_Entry {
        type string;
      }
    }
    leaf BPDUGuard {
      type PortConfigBPDUGuardTypeOptions;
    }
  }
  /* core/stp/stp.proto */
  grouping STPConfigMSTPGroupEntry {
    leaf MSTPID {
      type int32;
    }
    leaf BridgePriority {
      type int32;
    }
    container VIDs {
      leaf-list VIDs_Entry {
        type int32;
      }
    }
  }
  /* core/stp/stp.proto */
  grouping STPConfig {
    container Bridge {
      uses STPConfigBridge;
    }
    container Ports {
      list Ports_Entry {
        uses STPConfigPortEntry;
      }
    }
    container MSTPGroups {
      list MSTPGroups_Entry {
        uses STPConfigMSTPGroupEntry;
      }
    }
  }
  /* core/stp/stp.proto */
  grouping BridgeConfigMode {
    leaf Mode {
      type BridgeConfigModeTypeOptions;
    }
  }
  /* core/stp/stp.proto */
  grouping BridgeConfigPriority {
    leaf Priority {
      type int32;
    }
  }
  /* core/stp/stp.proto */
  grouping BridgeConfigHelloTime {
    leaf HelloTime {
      type int32;
    }
  }
  /* core/stp/stp.proto */
  grouping BridgeConfigMaxAge {
    leaf MaxAge {
      type int32;
    }
  }
  /* core/stp/stp.proto */
  grouping BridgeConfigForwardDelay {
    leaf ForwardDelay {
      type int32;
    }
  }
  /* core/stp/stp.proto */
  grouping BridgeConfigTxHoldCount {
    leaf TxHoldCount {
      type int32;
    }
  }
  /* core/stp/stp.proto */
  grouping BridgeConfigMSTPRegionName {
    leaf MSTPRegionName {
      type string;
    }
  }
  /* core/stp/stp.proto */
  grouping BridgeConfigMSTPRevisionLevel {
    leaf MSTPRevisionLevel {
      type int32;
    }
  }
  /* core/stp/stp.proto */
  grouping BridgeConfigMSTPMaxHops {
    leaf MSTPMaxHops {
      type int32;
    }
  }
  /* core/stp/stp.proto */
  grouping STPPortConfigEnabledEntry {
    leaf PortNo {
      type int32;
    }
    leaf Enabled {
      type boolean;
    }
  }
  /* core/stp/stp.proto */
  grouping STPPortConfigEnabled {
    container List {
      list List_Entry {
        uses STPPortConfigEnabledEntry;
      }
    }
  }
  /* core/stp/stp.proto */
  grouping STPPortConfigPriorityEntry {
    leaf PortNo {
      type int32;
    }
    leaf Priority {
      type int32;
    }
  }
  /* core/stp/stp.proto */
  grouping STPPortConfigPriority {
    container List {
      list List_Entry {
        uses STPPortConfigPriorityEntry;
      }
    }
  }
  /* core/stp/stp.proto */
  grouping STPPortConfigAdminP2PPortEntry {
    leaf PortNo {
      type int32;
    }
    leaf AdminP2PPort {
      type PortConfigAdminP2PPortTypeOptions;
    }
  }
  /* core/stp/stp.proto */
  grouping STPPortConfigAdminP2PPort {
    container List {
      list List_Entry {
        uses STPPortConfigAdminP2PPortEntry;
      }
    }
  }
  /* core/stp/stp.proto */
  grouping STPPortConfigAdminEdgePortEntry {
    leaf PortNo {
      type int32;
    }
    leaf AdminEdgePort {
      type boolean;
    }
  }
  /* core/stp/stp.proto */
  grouping STPPortConfigAdminEdgePort {
    container List {
      list List_Entry {
        uses STPPortConfigAdminEdgePortEntry;
      }
    }
  }
  /* core/stp/stp.proto */
  grouping STPPortConfigAdminPathCostEntry {
    leaf PortNo {
      type int32;
    }
    leaf AdminPathCost {
      type int32;
    }
  }
  /* core/stp/stp.proto */
  grouping STPPortConfigAdminPathCost {
    container List {
      list List_Entry {
        uses STPPortConfigAdminPathCostEntry;
      }
    }
  }
  /* core/stp/stp.proto */
  grouping STPPortConfigMSTPDefaultPriorityEntry {
    leaf PortNo {
      type int32;
    }
    leaf MSTPDefaultPriority {
      type int32;
    }
  }
  /* core/stp/stp.proto */
  grouping STPPortConfigMSTPDefaultPriority {
    container List {
      list List_Entry {
        uses STPPortConfigMSTPDefaultPriorityEntry;
      }
    }
  }
  /* core/stp/stp.proto */
  grouping STPPortConfigMSTPPortPriorityEntry {
    leaf PortNo {
      type int32;
    }
    container MSTPPortPriority {
      leaf-list MSTPPortPriority_Entry {
        type string;
      }
    }
  }
  /* core/stp/stp.proto */
  grouping STPPortConfigMSTPPortPriority {
    container List {
      list List_Entry {
        uses STPPortConfigMSTPPortPriorityEntry;
      }
    }
  }
  /* core/stp/stp.proto */
  grouping STPPortConfigMSTPDefaultAdminPathCostEntry {
    leaf PortNo {
      type int32;
    }
    leaf MSTPDefaultAdminPathCost {
      type int32;
    }
  }
  /* core/stp/stp.proto */
  grouping STPPortConfigMSTPDefaultAdminPathCost {
    container List {
      list List_Entry {
        uses STPPortConfigMSTPDefaultAdminPathCostEntry;
      }
    }
  }
  /* core/stp/stp.proto */
  grouping STPPortConfigMSTPPortAdminPathCostEntry {
    leaf PortNo {
      type int32;
    }
    container MSTPPortAdminPathCost {
      leaf-list MSTPPortAdminPathCost_Entry {
        type string;
      }
    }
  }
  /* core/stp/stp.proto */
  grouping STPPortConfigMSTPPortAdminPathCost {
    container List {
      list List_Entry {
        uses STPPortConfigMSTPPortAdminPathCostEntry;
      }
    }
  }
  /* core/stp/stp.proto */
  grouping STPPortConfigBPDUGuardEntry {
    leaf PortNo {
      type int32;
    }
    leaf BPDUGuard {
      type PortConfigBPDUGuardTypeOptions;
    }
  }
  /* core/stp/stp.proto */
  grouping STPPortConfigBPDUGuard {
    container List {
      list List_Entry {
        uses STPPortConfigBPDUGuardEntry;
      }
    }
  }
  /* core/stp/stp.proto */
  grouping STPPortConfigBPDUReceiveOnlyEntry {
    leaf PortNo {
      type int32;
    }
    leaf BPDUReceiveOnly {
      type boolean;
    }
  }
  /* core/stp/stp.proto */
  grouping STPPortConfigBPDUReceiveOnly {
    container List {
      list List_Entry {
        uses STPPortConfigBPDUReceiveOnlyEntry;
      }
    }
  }
  /* core/stp/stp.proto */
  grouping STPPortConfigRestrictTcnEntry {
    leaf PortNo {
      type int32;
    }
    leaf RestrictTcn {
      type boolean;
    }
  }
  /* core/stp/stp.proto */
  grouping STPPortConfigRestrictTcn {
    container List {
      list List_Entry {
        uses STPPortConfigRestrictTcnEntry;
      }
    }
  }
  /* core/stp/stp.proto */
  grouping STPPortConfigRestrictRootEntry {
    leaf PortNo {
      type int32;
    }
    leaf RestrictRoot {
      type boolean;
    }
  }
  /* core/stp/stp.proto */
  grouping STPPortConfigRestrictRoot {
    container List {
      list List_Entry {
        uses STPPortConfigRestrictRootEntry;
      }
    }
  }
  /* core/stp/stp.proto */
  grouping MSTPIDList {
    container IDList {
      leaf-list IDList_Entry {
        type int32;
      }
    }
  }
  /* core/stp/stp.proto */
  grouping STPMSTPGroupEntry {
    leaf MSTPID {
      type int32;
    }
    leaf BridgePriority {
      type int32;
    }
    container VIDs {
      leaf-list VIDs_Entry {
        type int32;
      }
    }
  }
  /* core/stp/stp.proto */
  grouping MSTPGroup {
    container List {
      list List_Entry {
        uses STPMSTPGroupEntry;
      }
    }
  }


  /* **************************************************************************************************
   * Services    : 1                                                                                  *
   ************************************************************************************************** */

  /* **************************************************************************************************
   * Service     : MSTP                                                                               *
   * Methods     : 54                                                                                 *
   ************************************************************************************************** */
  /* core/stp/service.proto */
  rpc intri-stp-GetConfig {
    output  {
      uses MSTPConfig;
    }
  }
  /* core/stp/service.proto */
  rpc intri-stp-SetConfig {
    input  {
      uses MSTPConfig;
    }
  }
  /* core/stp/service.proto */
  rpc intri-stp-SetCistConfig {
    input  {
      uses CISTEntry;
    }
  }
  /* core/stp/service.proto */
  rpc intri-stp-SetMstiConfig {
    input  {
      uses MSTIList;
    }
  }
  /* core/stp/service.proto */
  rpc intri-stp-GetCistStatus {
    output  {
      uses CISTStatus;
    }
  }
  /* core/stp/service.proto */
  rpc intri-stp-GetMstiStatus {
    output  {
      uses MSTIStatus;
    }
  }
  /* core/stp/service.proto */
  rpc intri-stp-RunReconfigPortState {
  }
  /* core/stp/service.proto */
  rpc intri-stp-GetBridgeConfigMode {
    output  {
      uses BridgeConfigMode;
    }
  }
  /* core/stp/service.proto */
  rpc intri-stp-SetBridgeConfigMode {
    input  {
      uses BridgeConfigMode;
    }
  }
  /* core/stp/service.proto */
  rpc intri-stp-GetBridgeConfigPriority {
    output  {
      uses BridgeConfigPriority;
    }
  }
  /* core/stp/service.proto */
  rpc intri-stp-SetBridgeConfigPriority {
    input  {
      uses BridgeConfigPriority;
    }
  }
  /* core/stp/service.proto */
  rpc intri-stp-GetBridgeConfigHelloTime {
    output  {
      uses BridgeConfigHelloTime;
    }
  }
  /* core/stp/service.proto */
  rpc intri-stp-SetBridgeConfigHelloTime {
    input  {
      uses BridgeConfigHelloTime;
    }
  }
  /* core/stp/service.proto */
  rpc intri-stp-GetBridgeConfigMaxAge {
    output  {
      uses BridgeConfigMaxAge;
    }
  }
  /* core/stp/service.proto */
  rpc intri-stp-SetBridgeConfigMaxAge {
    input  {
      uses BridgeConfigMaxAge;
    }
  }
  /* core/stp/service.proto */
  rpc intri-stp-GetBridgeConfigForwardDelay {
    output  {
      uses BridgeConfigForwardDelay;
    }
  }
  /* core/stp/service.proto */
  rpc intri-stp-SetBridgeConfigForwardDelay {
    input  {
      uses BridgeConfigForwardDelay;
    }
  }
  /* core/stp/service.proto */
  rpc intri-stp-GetBridgeConfigTxHoldCount {
    output  {
      uses BridgeConfigTxHoldCount;
    }
  }
  /* core/stp/service.proto */
  rpc intri-stp-SetBridgeConfigTxHoldCount {
    input  {
      uses BridgeConfigTxHoldCount;
    }
  }
  /* core/stp/service.proto */
  rpc intri-stp-GetBridgeConfigMSTPRegionName {
    output  {
      uses BridgeConfigMSTPRegionName;
    }
  }
  /* core/stp/service.proto */
  rpc intri-stp-SetBridgeConfigMSTPRegionName {
    input  {
      uses BridgeConfigMSTPRegionName;
    }
  }
  /* core/stp/service.proto */
  rpc intri-stp-GetBridgeConfigMSTPRevisionLevel {
    output  {
      uses BridgeConfigMSTPRevisionLevel;
    }
  }
  /* core/stp/service.proto */
  rpc intri-stp-SetBridgeConfigMSTPRevisionLevel {
    input  {
      uses BridgeConfigMSTPRevisionLevel;
    }
  }
  /* core/stp/service.proto */
  rpc intri-stp-GetBridgeConfigMSTPMaxHops {
    output  {
      uses BridgeConfigMSTPMaxHops;
    }
  }
  /* core/stp/service.proto */
  rpc intri-stp-SetBridgeConfigMSTPMaxHops {
    input  {
      uses BridgeConfigMSTPMaxHops;
    }
  }
  /* core/stp/service.proto */
  rpc intri-stp-GetPortConfigEnabled {
    input  {
      uses intri-device:PortList;
    }
    output  {
      uses STPPortConfigEnabled;
    }
  }
  /* core/stp/service.proto */
  rpc intri-stp-SetPortConfigEnabled {
    input  {
      uses STPPortConfigEnabled;
    }
  }
  /* core/stp/service.proto */
  rpc intri-stp-GetPortConfigPriority {
    input  {
      uses intri-device:PortList;
    }
    output  {
      uses STPPortConfigPriority;
    }
  }
  /* core/stp/service.proto */
  rpc intri-stp-SetPortConfigPriority {
    input  {
      uses STPPortConfigPriority;
    }
  }
  /* core/stp/service.proto */
  rpc intri-stp-GetPortConfigAdminP2PPort {
    input  {
      uses intri-device:PortList;
    }
    output  {
      uses STPPortConfigAdminP2PPort;
    }
  }
  /* core/stp/service.proto */
  rpc intri-stp-SetPortConfigAdminP2PPort {
    input  {
      uses STPPortConfigAdminP2PPort;
    }
  }
  /* core/stp/service.proto */
  rpc intri-stp-GetPortConfigAdminEdgePort {
    input  {
      uses intri-device:PortList;
    }
    output  {
      uses STPPortConfigAdminEdgePort;
    }
  }
  /* core/stp/service.proto */
  rpc intri-stp-SetPortConfigAdminEdgePort {
    input  {
      uses STPPortConfigAdminEdgePort;
    }
  }
  /* core/stp/service.proto */
  rpc intri-stp-GetPortConfigAdminPathCost {
    input  {
      uses intri-device:PortList;
    }
    output  {
      uses STPPortConfigAdminPathCost;
    }
  }
  /* core/stp/service.proto */
  rpc intri-stp-SetPortConfigAdminPathCost {
    input  {
      uses STPPortConfigAdminPathCost;
    }
  }
  /* core/stp/service.proto */
  rpc intri-stp-GetPortConfigMSTPDefaultPriority {
    input  {
      uses intri-device:PortList;
    }
    output  {
      uses STPPortConfigMSTPDefaultPriority;
    }
  }
  /* core/stp/service.proto */
  rpc intri-stp-SetPortConfigMSTPDefaultPriority {
    input  {
      uses STPPortConfigMSTPDefaultPriority;
    }
  }
  /* core/stp/service.proto */
  rpc intri-stp-GetPortConfigMSTPPortPriority {
    input  {
      uses intri-device:PortList;
    }
    output  {
      uses STPPortConfigMSTPPortPriority;
    }
  }
  /* core/stp/service.proto */
  rpc intri-stp-SetPortConfigMSTPPortPriority {
    input  {
      uses STPPortConfigMSTPPortPriority;
    }
  }
  /* core/stp/service.proto */
  rpc intri-stp-GetPortConfigMSTPDefaultAdminPathCost {
    input  {
      uses intri-device:PortList;
    }
    output  {
      uses STPPortConfigMSTPDefaultAdminPathCost;
    }
  }
  /* core/stp/service.proto */
  rpc intri-stp-SetPortConfigMSTPDefaultAdminPathCost {
    input  {
      uses STPPortConfigMSTPDefaultAdminPathCost;
    }
  }
  /* core/stp/service.proto */
  rpc intri-stp-GetPortConfigMSTPPortAdminPathCost {
    input  {
      uses intri-device:PortList;
    }
    output  {
      uses STPPortConfigMSTPPortAdminPathCost;
    }
  }
  /* core/stp/service.proto */
  rpc intri-stp-SetPortConfigMSTPPortAdminPathCost {
    input  {
      uses STPPortConfigMSTPPortAdminPathCost;
    }
  }
  /* core/stp/service.proto */
  rpc intri-stp-GetPortConfigBPDUGuard {
    input  {
      uses intri-device:PortList;
    }
    output  {
      uses STPPortConfigBPDUGuard;
    }
  }
  /* core/stp/service.proto */
  rpc intri-stp-SetPortConfigBPDUGuard {
    input  {
      uses STPPortConfigBPDUGuard;
    }
  }
  /* core/stp/service.proto */
  rpc intri-stp-GetPortConfigBPDUReceiveOnly {
    input  {
      uses intri-device:PortList;
    }
    output  {
      uses STPPortConfigBPDUReceiveOnly;
    }
  }
  /* core/stp/service.proto */
  rpc intri-stp-SetPortConfigBPDUReceiveOnly {
    input  {
      uses STPPortConfigBPDUReceiveOnly;
    }
  }
  /* core/stp/service.proto */
  rpc intri-stp-GetPortConfigRestrictTcn {
    input  {
      uses intri-device:PortList;
    }
    output  {
      uses STPPortConfigRestrictTcn;
    }
  }
  /* core/stp/service.proto */
  rpc intri-stp-SetPortConfigRestrictTcn {
    input  {
      uses STPPortConfigRestrictTcn;
    }
  }
  /* core/stp/service.proto */
  rpc intri-stp-GetPortConfigRestrictRoot {
    input  {
      uses intri-device:PortList;
    }
    output  {
      uses STPPortConfigRestrictRoot;
    }
  }
  /* core/stp/service.proto */
  rpc intri-stp-SetPortConfigRestrictRoot {
    input  {
      uses STPPortConfigRestrictRoot;
    }
  }
  /* core/stp/service.proto */
  rpc intri-stp-GetMSTPGroup {
    input  {
      uses MSTPIDList;
    }
    output  {
      uses MSTPGroup;
    }
  }
  /* core/stp/service.proto */
  rpc intri-stp-SetMSTPGroup {
    input  {
      uses MSTPGroup;
    }
  }
  /* core/stp/service.proto */
  rpc intri-stp-DeleteMSTPGroup {
    input  {
      uses MSTPIDList;
    }
  }

}
