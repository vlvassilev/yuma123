// Code generated by protoc-gen-yang. DO NOT EDIT.


/* ****************************************************************************************************
 * Import Path : "github.com/golang/protobuf/ptypes/empty"                                            *
 * Dir Path    : github.com/golang/protobuf/ptypes/empty                                              *
 * Go Package  : empty                                                                                *
 * Files       : 1                                                                                    *
 **************************************************************************************************** */
module intri-empty {

  namespace "intri:intri-empty";

  prefix "intri-empty";

  organization "Intrising Inc.";

  contact "intrising@intrising.com.tw";

  revision 2022-06-23 {
    description "Build date.";
  }


  /* **************************************************************************************************
   * Msgs        : 1                                                                                  *
   ************************************************************************************************** */
  /* google/protobuf/empty.proto */
  grouping Empty {
  }

}
