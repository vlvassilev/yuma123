module testaugbug {

    namespace "http://netconfcentral.com/ns/testaugbug";
    prefix "r1";

    import testr2 {
        prefix r2;
        revision-date 2009-01-01;
    }

    organization
        "Netconf Central";

    contact
        "Andy Bierman";

    description
        "YANG import-by-revision test module.";

    revision 2009-02-02 {
        description "Initial version.";
    }
  
    grouping TestGroup1 {
       leaf X { type string; }
       leaf Y { type leafref { path "../X"; } }
       uses r2:TestGroup {
         augment E {
           when "../Y = 'fred'";
           container Z {
             presence "exists";
           }
         }
      }
    }

    container goo-local {
       uses r1:TestGroup1;
    }

    
}
