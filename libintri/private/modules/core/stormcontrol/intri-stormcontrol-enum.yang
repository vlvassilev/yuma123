submodule intri-stormcontrol-enum {
  belongs-to "intri-stormcontrol" {
    prefix "intri-stormcontrol-enum";
  }
  revision 2022-06-14 {
    description "Build date.";
  }
  // core/stormcontrol/stormcontrol.proto
  typedef StormControlActionTypeOptions {
    type enumeration {
      enum STORM_CONTROL_ACTION_TYPE_SHUTDOWN {
        description "[Shutdown] the port interface will be shutdown when the percent of the outputed packet is over the max level";
        value 0;
      }
      enum STORM_CONTROL_ACTION_TYPE_BLOCKING {
        description "[Blocking] the port interface will be blocking when the percent of the outputed packet is over the max level";
        value 1;
      }
    }
  }
  // core/stormcontrol/stormcontrol.proto
  typedef StormControlSuppressionTypeOptions {
    type enumeration {
      enum STORM_CONTROL_SUPPRESSION_TYPE_BROADCAST {
        description "[Broadcast] counter forwards broadcast bits/packets per second of lading as the standard";
        value 0;
      }
      enum STORM_CONTROL_SUPPRESSION_TYPE_MULTICAST {
        description "[Multicast] counter forwards multicast bits/packets per second of lading as the standard";
        value 1;
      }
      enum STORM_CONTROL_SUPPRESSION_TYPE_UNKNOWN_UNICAST {
        description "[Unknown Unicast] counter forwards unknown unicast bits/packets per second of lading as the standard";
        value 2;
      }
    }
  }
  // core/stormcontrol/stormcontrol.proto
  typedef StormControlSuppressionUnitTypeOptions {
    type enumeration {
      enum STORM_CONTROL_SUPPRESSION_TYPE_BITS_PER_SECOND {
        description "[bits/sec.] counter bits per secound";
        value 0;
      }
      enum STORM_CONTROL_SUPPRESSION_TYPE_PACKETS_PER_SECOND {
        description "[packets/sec.] counter packets per secound";
        value 1;
      }
    }
  }
}
