// Code generated by protoc-gen-yang. DO NOT EDIT.


/* ****************************************************************************************************
 * Import Path : "github.com/Intrising/intri-type/common"                                             *
 * Dir Path    : github.com/Intrising/intri-type/common                                               *
 * Go Package  : common                                                                               *
 * Files       : 3                                                                                    *
 **************************************************************************************************** */
module intri-common {

  namespace "intri:intri-common";

  prefix "intri-common";

  organization "Intrising Inc.";

  contact "intrising@intrising.com.tw";

  revision 2022-06-23 {
    description "Build date.";
  }


  /* **************************************************************************************************
   * Enums       : 3                                                                                  *
   ************************************************************************************************** */
  /* common/common.proto */
  typedef IPv6ScopeTypeOptions {
    type enumeration {
      enum IPV6_SCOPE_TYPE_LINK {
        description "[Link]";
        value 0;
      }
      enum IPV6_SCOPE_TYPE_SITE {
        description "[Site]";
        value 1;
      }
      enum IPV6_SCOPE_TYPE_GLOBAL {
        description "[Global]";
        value 2;
      }
      enum IPV6_SCOPE_TYPE_OTHER {
        description "[Other]";
        value 3;
      }
    }
  }
  /* common/error.proto */
  typedef VlanServiceErrorOptions {
    type enumeration {
      enum MAC_BASED_ADD_LIST_OUT_OF_RANGE {
        description "";
        value 0;
      }
      enum MAC_BASED_ADD_GROUP_ID_OUT_OF_RANGE {
        description "";
        value 1;
      }
      enum MAC_BASED_ADD_GROUP_ID_EXIST {
        description "";
        value 2;
      }
      enum MAC_BASED_ADD_MAC_ADDRESS_INVALID {
        description "";
        value 3;
      }
      enum MAC_BASED_ADD_MAC_ADDRESS_MASK_INVALID {
        description "";
        value 4;
      }
    }
  }
  /* common/service.proto */
  typedef ServicesEnumTypeOptions {
    type enumeration {
      enum SERVICES_ENUM_TYPE_ALL {
        description "";
        value 0;
      }
      enum SERVICES_ENUM_TYPE_EVENT {
        description "";
        value 1;
      }
      enum SERVICES_ENUM_TYPE_PACKET {
        description "";
        value 2;
      }
      enum SERVICES_ENUM_TYPE_CONFIG {
        description "";
        value 3;
      }
      enum SERVICES_ENUM_TYPE_LOG {
        description "";
        value 4;
      }
      enum SERVICES_ENUM_TYPE_DEVICE {
        description "";
        value 10;
      }
      enum SERVICES_ENUM_TYPE_DEVICE_FUNCTION_CONTROL {
        description "";
        value 11;
      }
      enum SERVICES_ENUM_TYPE_CPSS {
        description "";
        value 20;
      }
      enum SERVICES_ENUM_TYPE_CPSS_ACL {
        description "";
        value 21;
      }
      enum SERVICES_ENUM_TYPE_CPSS_DEVICE {
        description "";
        value 22;
      }
      enum SERVICES_ENUM_TYPE_CPSS_BOARD {
        description "";
        value 23;
      }
      enum SERVICES_ENUM_TYPE_CPSS_FDB {
        description "";
        value 24;
      }
      enum SERVICES_ENUM_TYPE_CPSS_MIRRORING {
        description "";
        value 25;
      }
      enum SERVICES_ENUM_TYPE_CPSS_MISC {
        description "";
        value 26;
      }
      enum SERVICES_ENUM_TYPE_CPSS_MULTICAST {
        description "";
        value 27;
      }
      enum SERVICES_ENUM_TYPE_CPSS_PORT {
        description "";
        value 28;
      }
      enum SERVICES_ENUM_TYPE_CPSS_QOS {
        description "";
        value 29;
      }
      enum SERVICES_ENUM_TYPE_CPSS_RATELIMITING {
        description "";
        value 30;
      }
      enum SERVICES_ENUM_TYPE_CPSS_STP {
        description "";
        value 31;
      }
      enum SERVICES_ENUM_TYPE_CPSS_TRUNKING {
        description "";
        value 32;
      }
      enum SERVICES_ENUM_TYPE_CPSS_VLAN {
        description "";
        value 33;
      }
      enum SERVICES_ENUM_TYPE_CPSS_PACKET_CONTROL {
        description "";
        value 34;
      }
      enum SERVICES_ENUM_TYPE_CPSS_PTP {
        description "";
        value 35;
      }
      enum SERVICES_ENUM_TYPE_CPSS_CNC {
        description "";
        value 36;
      }
      enum SERVICES_ENUM_TYPE_CPSS_POLICER {
        description "";
        value 37;
      }
      enum SERVICES_ENUM_TYPE_HARDWARE {
        description "";
        value 40;
      }
      enum SERVICES_ENUM_TYPE_CLI {
        description "";
        value 41;
      }
      enum SERVICES_ENUM_TYPE_SNMP {
        description "";
        value 42;
      }
      enum SERVICES_ENUM_TYPE_WEB {
        description "";
        value 43;
      }
      enum SERVICES_ENUM_TYPE_SSH {
        description "";
        value 44;
      }
      enum SERVICES_ENUM_TYPE_TELNET {
        description "";
        value 45;
      }
      enum SERVICES_ENUM_TYPE_CONSOLE {
        description "";
        value 46;
      }
      enum SERVICES_ENUM_TYPE_UNKNOWN {
        description "";
        value 47;
      }
      enum SERVICES_ENUM_TYPE_GATEWAY {
        description "";
        value 48;
      }
      enum SERVICES_ENUM_TYPE_RESTAPI {
        description "";
        value 49;
      }
      enum SERVICES_ENUM_TYPE_CORE_VLAN {
        description "";
        value 50;
      }
      enum SERVICES_ENUM_TYPE_CORE_VLAN_GVRP {
        description "";
        value 51;
      }
      enum SERVICES_ENUM_TYPE_CORE_ACL {
        description "";
        value 60;
      }
      enum SERVICES_ENUM_TYPE_CORE_ACL_STORMCONTROL {
        description "";
        value 61;
      }
      enum SERVICES_ENUM_TYPE_CORE_ACCESS {
        description "";
        value 70;
      }
      enum SERVICES_ENUM_TYPE_CORE_ACCESS_USER_INTERFACE {
        description "";
        value 71;
      }
      enum SERVICES_ENUM_TYPE_CORE_AU {
        description "";
        value 80;
      }
      enum SERVICES_ENUM_TYPE_CORE_AU_SECURITY {
        description "";
        value 81;
      }
      enum SERVICES_ENUM_TYPE_CORE_AUTHENTICATION_PORT {
        description "";
        value 82;
      }
      enum SERVICES_ENUM_TYPE_CORE_SYSTEM {
        description "";
        value 90;
      }
      enum SERVICES_ENUM_TYPE_CORE_SYSTEM_DIAGNOSTIC {
        description "";
        value 91;
      }
      enum SERVICES_ENUM_TYPE_CORE_SYSTEM_MAINTENANCE {
        description "";
        value 92;
      }
      enum SERVICES_ENUM_TYPE_CORE_SYSTEM_TIME_RANGE {
        description "";
        value 93;
      }
      enum SERVICES_ENUM_TYPE_CORE_SYSTEM_FILES {
        description "";
        value 94;
      }
      enum SERVICES_ENUM_TYPE_CORE_LACP {
        description "";
        value 100;
      }
      enum SERVICES_ENUM_TYPE_CORE_PORT {
        description "";
        value 110;
      }
      enum SERVICES_ENUM_TYPE_CORE_PORT_RMON {
        description "";
        value 111;
      }
      enum SERVICES_ENUM_TYPE_CORE_PORT_SFP {
        description "";
        value 112;
      }
      enum SERVICES_ENUM_TYPE_CORE_PORT_ISOLATION {
        description "";
        value 113;
      }
      enum SERVICES_ENUM_TYPE_CORE_PORT_MIRRORING {
        description "";
        value 114;
      }
      enum SERVICES_ENUM_TYPE_CORE_MULTICAST {
        description "";
        value 120;
      }
      enum SERVICES_ENUM_TYPE_CORE_DHCP {
        description "";
        value 130;
      }
      enum SERVICES_ENUM_TYPE_CORE_QOS {
        description "";
        value 140;
      }
      enum SERVICES_ENUM_TYPE_CORE_NETWORK {
        description "";
        value 150;
      }
      enum SERVICES_ENUM_TYPE_CORE_TIME {
        description "";
        value 160;
      }
      enum SERVICES_ENUM_TYPE_CORE_LOOP {
        description "";
        value 170;
      }
      enum SERVICES_ENUM_TYPE_CORE_LLDP {
        description "";
        value 180;
      }
      enum SERVICES_ENUM_TYPE_CORE_POE {
        description "";
        value 181;
      }
      enum SERVICES_ENUM_TYPE_CORE_STP {
        description "";
        value 182;
      }
      enum SERVICES_ENUM_TYPE_CORE_CDP {
        description "";
        value 183;
      }
      enum SERVICES_ENUM_TYPE_HARDWARE_POE {
        description "";
        value 184;
      }
      enum SERVICES_ENUM_TYPE_CORE_MONITOR {
        description "";
        value 185;
      }
      enum SERVICES_ENUM_TYPE_CORE_UDLD {
        description "";
        value 186;
      }
      enum SERVICES_ENUM_TYPE_CORE_PTP {
        description "";
        value 190;
      }
      enum SERVICES_ENUM_TYPE_TIME_CONTROL {
        description "";
        value 200;
      }
      enum SERVICES_ENUM_TYPE_QT_CLI {
        description "";
        value 210;
      }
      enum SERVICES_ENUM_TYPE_SNMP_TRAP {
        description "add the same prefix with snmp";
        value 221;
      }
    }
  }


  /* **************************************************************************************************
   * Msgs        : 18                                                                                 *
   ************************************************************************************************** */
  /* common/common.proto */
  grouping Path {
    leaf Path {
      type string;
    }
  }
  /* common/common.proto */
  grouping ExportPathRequest {
    leaf Path {
      type string;
    }
    leaf FTPSEnabled {
      type boolean;
    }
  }
  /* common/common.proto */
  grouping ImportPathRequest {
    leaf Path {
      type string;
    }
    leaf FTPSEnabled {
      type boolean;
    }
    leaf RebootAfterAction {
      type boolean;
    }
  }
  /* common/common.proto */
  grouping Enabled {
    leaf IsEnabled {
      type boolean;
    }
  }
  /* common/common.proto */
  grouping MACAddress {
    leaf MACAddr {
      type string;
    }
  }
  /* common/common.proto */
  grouping IPAddress {
    leaf IPAddr {
      type string;
    }
  }
  /* common/common.proto */
  grouping IPv4List {
    container List {
      leaf-list List_Entry {
        type string;
      }
    }
  }
  /* common/common.proto */
  grouping IPv6Entry {
    leaf Type {
      type IPv6ScopeTypeOptions;
    }
    leaf IPAddr {
      type string;
    }
  }
  /* common/common.proto */
  grouping IPv6List {
    container List {
      list List_Entry {
        uses IPv6Entry;
      }
    }
  }
  /* common/common.proto */
  grouping Name {
    leaf Name {
      type string;
    }
  }
  /* common/common.proto */
  grouping NameList {
    container NameList {
      leaf-list NameList_Entry {
        type string;
      }
    }
  }
  /* common/common.proto */
  grouping Reply {
    leaf Reply {
      type string;
    }
  }
  /* common/common.proto */
  grouping Confirm {
    leaf Confirm {
      type string;
    }
  }
  /* common/common.proto */
  grouping DateTime {
    leaf Ts {
      type string;
    }
  }
  /* common/common.proto */
  grouping AllStatus {
    leaf Status {
      type string;
    }
  }
  /* common/common.proto */
  grouping State {
    leaf State {
      type boolean;
    }
  }
  /* common/common.proto */
  grouping Index {
    leaf Index {
      type int32;
    }
  }
  /* common/error.proto */
  grouping GRPCErrorDetail {
    leaf FieldName {
      type string;
    }
    leaf FieldValue {
      type string;
    }
    leaf Description {
      type string;
    }
  }

}
