module intri-cpss {

  namespace "intri:intri-cpss";
  prefix "intri-cpss";
  organization "
    Intrising Inc.";
  contact "
    intrising@intrising.com.tw";
  revision 2022-06-24 {
    description "Build date.";
  }

  import intri-empty {
    prefix intri-empty;
    revision-date "2022-06-24";
  }
  typedef ActionTypeOptions {
    type enumeration {
      enum ACTION_TYPE_ADD {
        description "[Add] Action type add";
        value 0;
      }
      enum ACTION_TYPE_DELETE {
        description "[Delete] Action type delete";
        value 1;
      }
      enum ACTION_TYPE_UPDATE {
        description "[Update] Action type update";
        value 2;
      }
      enum ACTION_TYPE_GET {
        description "[Get] Action type get";
        value 3;
      }
    }
  }
  typedef InterfaceTypeOptions {
    type enumeration {
      enum INTERFACE_TYPE_VLAN {
        description "[Vlan] Interface type vlan";
        value 0;
      }
      enum INTERFACE_TYPE_PORT {
        description "[Port] Interface type port";
        value 1;
      }
      enum INTERFACE_TYPE_TRUNK {
        description "[Trunk] Interface type trunk";
        value 2;
      }
      enum INTERFACE_TYPE_VIDX {
        description "[Vidx] Interface type vidx";
        value 3;
      }
      enum INTERFACE_TYPE_MULTICAST {
        description "[Multicast] Interface type multicast";
        value 4;
      }
      enum INTERFACE_TYPE_VLAN_PORT {
        description "[Vlan Port] Interface type vlan port";
        value 5;
      }
      enum INTERFACE_TYPE_VLAN_TRUNK {
        description "[Vlan Trunk] Interface type vlan trunk";
        value 6;
      }
      enum INTERFACE_TYPE_PORT_TRUNK {
        description "[Port Trunk] Interface type port trunk";
        value 7;
      }
      enum INTERFACE_TYPE_ANY {
        description "[Any] Interface type any";
        value 8;
      }
    }
  }
  typedef PacketCommandOptions {
    type enumeration {
      enum PACKET_COMMAND_FORWARD {
        description "";
        value 0;
      }
      enum PACKET_COMMAND_MIRROR {
        description "";
        value 1;
      }
      enum PACKET_COMMAND_TRAP {
        description "";
        value 2;
      }
      enum PACKET_COMMAND_DROP {
        description "";
        value 3;
      }
    }
  }
  typedef PortSpeedDuplexOptions {
    type enumeration {
      enum PORT_SPEED_DUPLEX_AUTO {
        description "";
        value 0;
      }
      enum PORT_SPEED_DUPLEX_10M_FULL {
        description "";
        value 1;
      }
      enum PORT_SPEED_DUPLEX_100M_FULL {
        description "";
        value 3;
      }
      enum PORT_SPEED_DUPLEX_1000M_FULL {
        description "";
        value 5;
      }
      enum PORT_SPEED_DUPLEX_2500M_FULL {
        description "";
        value 6;
      }
      enum PORT_SPEED_DUPLEX_5G_FULL {
        description "";
        value 7;
      }
      enum PORT_SPEED_DUPLEX_10G_FULL {
        description "";
        value 8;
      }
      enum PORT_SPEED_DUPLEX_25G_FULL {
        description "";
        value 9;
      }
      enum PORT_SPEED_DUPLEX_40G_FULL {
        description "";
        value 10;
      }
      enum PORT_SPEED_DUPLEX_100G_FULL {
        description "";
        value 11;
      }
    }
  }
  typedef PortTypeOptions {
    type enumeration {
      enum PORT_TYPE_10M_FULL {
        description "[10 M Full] Port type 10 m full";
        value 0;
      }
      enum PORT_TYPE_100M_FULL {
        description "[100 M Full] Port type 100 m full";
        value 2;
      }
      enum PORT_TYPE_1000M_FULL {
        description "[1000 M Full] Port type 1000 m full";
        value 4;
      }
      enum PORT_TYPE_2500M_FULL {
        description "[2500 M Full] Port type 2500 m full";
        value 5;
      }
      enum PORT_TYPE_5G_FULL {
        description "[5 G Full] Port type 5 g full";
        value 6;
      }
      enum PORT_TYPE_10G_FULL {
        description "[10 G Full] Port type 10 g full";
        value 7;
      }
      enum PORT_TYPE_25G_FULL {
        description "[25 G Full] Port type 25 g full";
        value 8;
      }
      enum PORT_TYPE_40G_FULL {
        description "[40 G Full] Port type 40 g full";
        value 9;
      }
      enum PORT_TYPE_100G_FULL {
        description "[100 G Full] Port type 100 g full";
        value 10;
      }
    }
  }
  typedef PortMediaOptions {
    type enumeration {
      enum PORT_MEDIA_COPPER {
        description "";
        value 0;
      }
      enum PORT_MEDIA_RJ45 {
        description "";
        value 1;
      }
      enum PORT_MEDIA_SFP {
        description "";
        value 2;
      }
      enum PORT_MEDIA_STACKING {
        description "";
        value 3;
      }
      enum PORT_MEDIA_POE {
        description "";
        value 4;
      }
      enum PORT_MEDIA_POE_PLUS {
        description "";
        value 5;
      }
      enum PORT_MEDIA_POE_PLUS_PLUS {
        description "";
        value 6;
      }
      enum PORT_MEDIA_UP_LINK_PORT {
        description "";
        value 7;
      }
      enum PORT_MEDIA_DOWN_LINK_PORT {
        description "";
        value 8;
      }
    }
  }
  typedef STPProtocolTypeOptions {
    type enumeration {
      enum STP_PROTOCOL_TYPE_CPSS {
        description "[Cpss] Stp protocol type cpss";
        value 0;
      }
      enum STP_PROTOCOL_TYPE_DHCP {
        description "[Dhcp] Stp protocol type dhcp";
        value 10;
      }
      enum STP_PROTOCOL_TYPE_STORM_CONTROL {
        description "[Dhcp] Stp protocol type storm control";
        value 20;
      }
      enum STP_PROTOCOL_TYPE_LOOP {
        description "[Loop] Stp protocol type loop";
        value 30;
      }
      enum STP_PROTOCOL_TYPE_PORT {
        description "[Core] Stp protocol type port";
        value 40;
      }
      enum STP_PROTOCOL_TYPE_LACP {
        description "[Lacp] Stp protocol type lacp";
        value 70;
      }
      enum STP_PROTOCOL_TYPE_PACC {
        description "[Stp] Stp protocol type PACC";
        value 80;
      }
      enum STP_PROTOCOL_TYPE_STP {
        description "[Stp] Stp protocol type stp";
        value 90;
      }
      enum STP_PROTOCOL_TYPE_G8032 {
        description "[G8032] Stp protocol type g8032";
        value 100;
      }
    }
  }
  typedef STPPortStateTypeOptions {
    type enumeration {
      enum STP_PORT_STATE_TYPE_DISABLE {
        description "[Disable] Stp port state type disable";
        value 0;
      }
      enum STP_PORT_STATE_TYPE_BLOCKING {
        description "[Blocking] Stp port state type blocking";
        value 1;
      }
      enum STP_PORT_STATE_TYPE_LEARNING {
        description "[Learning] Stp port state type learning";
        value 2;
      }
      enum STP_PORT_STATE_TYPE_FORWARDING {
        description "[Forwarding] Stp port state type forwarding";
        value 3;
      }
    }
  }
  typedef ACLDirectionTypeOptions {
    type enumeration {
      enum ACL_DIRECTION_TYPE_INGRESS {
        description "[Ingress] Acl direction type ingress";
        value 0;
      }
      enum ACL_DIRECTION_TYPE_EGRESS {
        description "[Egress] Acl direction type egress";
        value 1;
      }
    }
  }
  typedef ACLRuleTypeOptions {
    type enumeration {
      enum ACL_RULE_TYPE_MAC {
        description "[Mac] Acl rule type mac";
        value 0;
      }
      enum ACL_RULE_TYPE_IPV4 {
        description "[Ipv4] Acl rule type ipv4";
        value 1;
      }
      enum ACL_RULE_TYPE_IPV6 {
        description "[Ipv6] Acl rule type ipv6";
        value 2;
      }
      enum ACL_RULE_TYPE_STP {
        description "[Stp] Acl rule type stp";
        value 3;
      }
      enum ACL_RULE_TYPE_LACP {
        description "[Lacp] Acl rule type lacp";
        value 4;
      }
      enum ACL_RULE_TYPE_DOT1X {
        description "[Dot1 X] Acl rule type dot1 x";
        value 5;
      }
      enum ACL_RULE_TYPE_ARP {
        description "[Arp] Acl rule type arp";
        value 6;
      }
      enum ACL_RULE_TYPE_DHCPV4_SRC_67_DST_68 {
        description "[Dhcpv4 Src 67 Dst 68] Acl rule type dhcpv4 src 67 dst 68";
        value 7;
      }
      enum ACL_RULE_TYPE_DHCPV4_SRC_68_DST_67 {
        description "[Dhcpv4 Src 68 Dst 67] Acl rule type dhcpv4 src 68 dst 67";
        value 8;
      }
      enum ACL_RULE_TYPE_LOOP {
        description "[Loop] Acl rule type loop";
        value 9;
      }
      enum ACL_RULE_TYPE_G8032 {
        description "[G8032] Acl rule type g8032";
        value 10;
      }
      enum ACL_RULE_TYPE_MAC_IP_BINDING {
        description "[Mac Ip Binding] Acl rule type mac ip binding";
        value 11;
      }
      enum ACL_RULE_TYPE_SUBNET_BASED {
        description "[Subnet Based] Acl rule type subnet based";
        value 12;
      }
      enum ACL_RULE_TYPE_MAC_BASED {
        description "[Mac Based] Acl rule type mac based";
        value 13;
      }
      enum ACL_RULE_TYPE_SELECTIVE_QINQ {
        description "[Selective Qinq] Acl rule type selective qinq";
        value 14;
      }
      enum ACL_RULE_TYPE_FLOW_MIRROR {
        description "[Flow Mirror] Acl rule type flow mirror";
        value 15;
      }
      enum ACL_RULE_TYPE_MAC_COUNTING {
        description "[Mac Counting] Acl rule type mac counting";
        value 16;
      }
      enum ACL_RULE_TYPE_PTP_MESSAGE {
        description "[PTP Message] Acl rule type ptp message";
        value 17;
      }
      enum ACL_RULE_TYPE_INCOMING_BLOCK {
        description "[Icoming Deny] Acl rule for deny the incoming packets";
        value 18;
      }
    }
  }
  typedef CNCCountingTypeOptions {
    type enumeration {
      enum CNC_COUNTING_TYPE_MAC_COUNTING {
        description "[Mac Counting] Cnc counting type mac counting";
        value 0;
      }
    }
  }
  typedef FDBLayerTypeOptions {
    type enumeration {
      enum FDB_LAYER_TYPE_2 {
        description "[Layer 2] FDB layer type 2";
        value 0;
      }
      enum FDB_LAYER_TYPE_3 {
        description "[Layer 3] FDB layer type 3";
        value 1;
      }
    }
  }
  typedef FDBEntryActionTypeOptions {
    type enumeration {
      enum FDB_ENTRY_ACTION_TYPE_ADD {
        description "[Add] FDB entry action type add";
        value 0;
      }
      enum FDB_ENTRY_ACTION_TYPE_DELETE {
        description "[Delete] FDB entry action type delete";
        value 1;
      }
    }
  }
  typedef MulticastEntryTypeOptions {
    type enumeration {
      enum MULTICAST_ENTRY_TYPE_MAC {
        description "[MAC] Multicast entry type mac";
        value 0;
      }
      enum MULTICAST_ENTRY_TYPE_IPV4 {
        description "[IPv4] Multicast entry type i pv4";
        value 1;
      }
      enum MULTICAST_ENTRY_TYPE_IPV6 {
        description "[IPv6] Multicast entry type i pv6";
        value 2;
      }
    }
  }
  typedef VIDXEntryTypeOptions {
    type enumeration {
      enum VIDX_ENTRY_TYPE_VLAN_FLOODING {
        description "";
        value 0;
      }
      enum VIDX_ENTRY_TYPE_BRIDGE_MULTICAST {
        description "";
        value 1;
      }
    }
  }
  typedef MirroringDirectionTypeOptions {
    type enumeration {
      enum MIRRORING_DIRECTION_TYPE_NONE {
        description "[None] Mirroring direction type none";
        value 0;
      }
      enum MIRRORING_DIRECTION_TYPE_TX_ONLY {
        description "[Tx Only] Mirroring direction type tx only";
        value 1;
      }
      enum MIRRORING_DIRECTION_TYPE_RX_ONLY {
        description "[Rx Only] Mirroring direction type rx only";
        value 2;
      }
      enum MIRRORING_DIRECTION_TYPE_BOTH {
        description "[Both] Mirroring direction type both";
        value 3;
      }
    }
  }
  typedef QoSTrustModeOptions {
    type enumeration {
      enum QOS_TRUST_MODE_DISABLED {
        description "[Disabled] Qos trust mode disabled";
        value 0;
      }
      enum QOS_TRUST_MODE_COS {
        description "[CoS] Qos trust mode cos";
        value 1;
      }
      enum QOS_TRUST_MODE_DSCP_ONLY {
        description "[DSCP Only] Qos trust mode dscp only";
        value 2;
      }
      enum QOS_TRUST_MODE_DSCP_FIRST {
        description "[DSCP First] Qos trust mode dscp first";
        value 3;
      }
    }
  }
  typedef QoSSchedulerTypeOptions {
    type enumeration {
      enum QOS_SCHEDULER_TYPE_WEIGHTED {
        description "[Weighted] Qos scheduler type weighted";
        value 0;
      }
      enum QOS_SCHEDULER_TYPE_STRICT {
        description "[Strict] Qos scheduler type strict";
        value 1;
      }
    }
  }
  typedef RateLimitingIngressFilterTypeOptions {
    type enumeration {
      enum RATE_LIMITING_INGRESS_FILTER_TYPE_UC_KNOWN {
        description "[UC Known] Rate limiting ingress filter type uc known";
        value 0;
      }
      enum RATE_LIMITING_INGRESS_FILTER_TYPE_UC_UNKNOWN {
        description "[UC Unknown] Rate limiting ingress filter type uc unknown";
        value 1;
      }
      enum RATE_LIMITING_INGRESS_FILTER_TYPE_MC_UNREGISTERED {
        description "[MC Unregistered] Rate limiting ingress filter type mc unregistered";
        value 2;
      }
      enum RATE_LIMITING_INGRESS_FILTER_TYPE_MC_REGISTERED {
        description "[MC Registered] Rate limiting ingress filter type mc registered";
        value 3;
      }
      enum RATE_LIMITING_INGRESS_FILTER_TYPE_BC {
        description "[BC] Rate limiting ingress filter type bc";
        value 4;
      }
    }
  }
  typedef TrunkingLoadBalanceModeOptions {
    type enumeration {
      enum TRUNKING_LOAD_BALANCE_MODE_SRC_DST_MAC {
        description "[Source/Destination MAC] Trunking load balance mode src dst mac";
        value 0;
      }
      enum TRUNKING_LOAD_BALANCE_MODE_SRC_DST_IP {
        description "[Source/Destination IP] Trunking load balance mode src dst ip";
        value 1;
      }
      enum TRUNKING_LOAD_BALANCE_MODE_SRC_DST_MAC_IP {
        description "[Source/Destination MAC and IP] Trunking load balance mode src dst mac ip";
        value 2;
      }
    }
  }
  typedef VlanTaggingCommandTypeOptions {
    type enumeration {
      enum VLAN_TAGGING_COMMAND_TYPE_UNTAGGED {
        description "[Untagged] Vlan tagging command type untagged";
        value 0;
      }
      enum VLAN_TAGGING_COMMAND_TYPE_TAGGED {
        description "[Tagged] Vlan tagging command type tagged";
        value 1;
      }
      enum VLAN_TAGGING_COMMAND_TYPE_QINQ_PROVIDER {
        description "[QinQ Provider] Vlan tagging command type qinq provider";
        value 2;
      }
      enum VLAN_TAGGING_COMMAND_TYPE_QINQ_CUSTOMER {
        description "[QinQ Customer] Vlan tagging command type qinq customer";
        value 3;
      }
    }
  }
  typedef VlanAcceptFrameTypeOptions {
    type enumeration {
      enum VLAN_ACCEPT_FRAME_TYPE_ALL {
        description "[All] Vlan accept frame type all";
        value 0;
      }
      enum VLAN_ACCEPT_FRAME_TYPE_UNTAGGED_ONLY {
        description "[Untagged Only] Vlan accept frame type untagged only";
        value 1;
      }
      enum VLAN_ACCEPT_FRAME_TYPE_TAGGED_ONLY {
        description "[Tagged Only] Vlan accept frame type tagged only";
        value 2;
      }
    }
  }
  typedef VlanTranslationMappingTypeOptions {
    type enumeration {
      enum VLAN_TRANSLATION_MAPPING_TYPE_ONE_TO_ONE {
        description "[One To One] Vlan translation mapping type one to one";
        value 0;
      }
      enum VLAN_TRANSLATION_MAPPING_TYPE_MANY_TO_ONE {
        description "[Many To One] Vlan translation mapping type many to one";
        value 1;
      }
    }
  }
  typedef VlanProtocolBasedEncapsulationTypeOptions {
    type enumeration {
      enum VLAN_PROTOCOL_BASED_ENCAPSULATION_ETHERNET_V2 {
        description "[Ethernet V2] Vlan protocol based encapsulation ethernet v2";
        value 0;
      }
      enum VLAN_PROTOCOL_BASED_ENCAPSULATION_NON_LLC_SNAP {
        description "[None LLC Snap] Vlan protocol based encapsulation non llc snap";
        value 1;
      }
      enum VLAN_PROTOCOL_BASED_ENCAPSULATION_LLC_SNAP {
        description "[LLC Snap] Vlan protocol based encapsulation llc snap";
        value 2;
      }
    }
  }
  typedef PacketControlProtocolTypeOptions {
    type enumeration {
      enum PACKET_CONTROL_PROTOCOL_TYPE_STP {
        description "[STP] Packet control protocol type stp";
        value 0;
      }
      enum PACKET_CONTROL_PROTOCOL_TYPE_LACP {
        description "[LACP] Packet control protocol type lacp";
        value 1;
      }
      enum PACKET_CONTROL_PROTOCOL_TYPE_DOT1X {
        description "[Dot1X] Packet control protocol type dot1 x";
        value 2;
      }
      enum PACKET_CONTROL_PROTOCOL_TYPE_LOOP {
        description "[Loop] Packet control protocol type loop";
        value 3;
      }
      enum PACKET_CONTROL_PROTOCOL_TYPE_DLDP {
        description "[DLDP] Packet control protocol type dldp";
        value 4;
      }
      enum PACKET_CONTROL_PROTOCOL_TYPE_DHCPV4_DISCOVER {
        description "[DHCP V4 Discover] Packet control protocol type dhcpv4 discover";
        value 5;
      }
      enum PACKET_CONTROL_PROTOCOL_TYPE_DHCPV4_BROADCAST_OFFER {
        description "[DHCP V4 Broadcast Offer] Packet control protocol type dhcpv4 broadcast offer";
        value 6;
      }
      enum PACKET_CONTROL_PROTOCOL_TYPE_DHCPV4_UDP_DST_67 {
        description "[DHCP V4 UDP Destination 67] Packet control protocol type dhcpv4 udp dst 67";
        value 7;
      }
      enum PACKET_CONTROL_PROTOCOL_TYPE_DHCPV4_UDP_DST_68 {
        description "[DHCP V4 UDP Destination 68] Packet control protocol type dhcpv4 udp dst 68";
        value 8;
      }
      enum PACKET_CONTROL_PROTOCOL_TYPE_ARP {
        description "[ARP] Packet control protocol type arp";
        value 9;
      }
      enum PACKET_CONTROL_PROTOCOL_TYPE_GVRP {
        description "[GVRP] Packet control protocol type gvrp";
        value 10;
      }
      enum PACKET_CONTROL_PROTOCOL_TYPE_IGMP {
        description "[IGMP] Packet control protocol type igmp";
        value 11;
      }
      enum PACKET_CONTROL_PROTOCOL_TYPE_MLD {
        description "[MLD] Packet control protocol type mld";
        value 12;
      }
    }
  }
  typedef PHYInterfaceTypeOptions {
    type enumeration {
      enum PHY_INTERFACE_TYPE_SMI {
        description "[SMI] Phy interface type smi";
        value 0;
      }
      enum PHY_INTERFACE_TYPE_XSMI {
        description "[XSMI] Phy interface type xsmi";
        value 1;
      }
      enum PHY_INTERFACE_TYPE_UNUSED {
        description "[Unused] Phy interface type unused";
        value 2;
      }
    }
  }
  typedef PTPSyncERecoveryClockSelectTypeOptions {
    type enumeration {
      enum PTP_SYNC_E_RECOVERY_CLOCK_SELECT_TYPE_0 {
        description "[Select Type 0] PTP sync e recovery clock select type 0";
        value 0;
      }
      enum PTP_SYNC_E_RECOVERY_CLOCK_SELECT_TYPE_1 {
        description "[Select Type 1] PTP sync e recovery clock select type 1";
        value 1;
      }
    }
  }
  typedef PTPPortDelayTypeOptions {
    type enumeration {
      enum PTP_PORT_DELAY_INGRESS {
        description "";
        value 0;
      }
      enum PTP_PORT_DELAY_EGRESS {
        description "";
        value 1;
      }
    }
  }
  typedef PTPModeTypeOptions {
    type enumeration {
      enum PTP_MODE_DISABLE {
        description "";
        value 0;
      }
      enum PTP_MODE_E2E_TC {
        description "";
        value 1;
      }
      enum PTP_MODE_P2P_TC {
        description "";
        value 2;
      }
      enum PTP_MODE_MASTER_BC {
        description "";
        value 3;
      }
      enum PTP_MODE_SLAVE_BC {
        description "";
        value 4;
      }
      enum PTP_MODE_GPTP_MASTER {
        description "";
        value 5;
      }
      enum PTP_MODE_GPTP_SLAVE {
        description "";
        value 6;
      }
      enum PTP_MODE_PASSIVE {
        description "";
        value 7;
      }
      enum PTP_MODE_LISTENING {
        description "";
        value 8;
      }
    }
  }
  grouping Enabled {
    leaf IsEnabled {
      type boolean;
    }
  }
  grouping IndexList {
    container List {
      leaf-list List_Entry {
        type int32;
      }
    }
  }
  grouping MACAddress {
    leaf Value {
      type string;
    }
  }
  grouping DeviceArchitecture {
    container Information {
      uses DeviceInformation;
    }
    container PortAllocationTable {
      uses DevicePortAllocationTable;
    }
  }
  grouping DeviceInformation {
    leaf Model {
      type string;
    }
    leaf MACAddress {
      type string;
    }
    leaf Description {
      type string;
    }
    leaf EnterpriseOID {
      type string;
    }
    leaf Vendor {
      type string;
    }
    leaf HardwareVersion {
      type string;
    }
    leaf SoftwareVersion {
      type string;
    }
  }
  grouping DevicePortProperty {
    leaf PortNo {
      type int32;
    }
    leaf Type {
      type PortTypeOptions;
    }
    leaf MACNo {
      type int32;
    }
    container PHYInterface {
      uses PHYInterface;
    }
    leaf PHYID1 {
      type int32;
    }
    leaf PHYID2 {
      type int32;
    }
    leaf PHYChipID {
      type int32;
    }
    leaf PoENo {
      type int32;
    }
    leaf PoEChipNo {
      type int32;
    }
    leaf PoELEDNo {
      type int32;
    }
    container SupportedTypeList {
      leaf-list SupportedTypeList_Entry {
        type PortTypeOptions;
      }
    }
    container SupportedMediaList {
      leaf-list SupportedMediaList_Entry {
        type PortMediaOptions;
      }
    }
  }
  grouping PHYInterface {
    leaf Interface {
      type int32;
    }
    leaf Type {
      type PHYInterfaceTypeOptions;
    }
  }
  grouping DevicePortAllocationTable {
    leaf CPUPortNo {
      type int32;
    }
    container PortPropertyList {
      list PortPropertyList_Entry {
        uses DevicePortProperty;
      }
    }
    container PortList {
      leaf-list PortList_Entry {
        type int32;
      }
    }
    container MACNoList {
      leaf-list MACNoList_Entry {
        type int32;
      }
    }
    container PoEList {
      leaf-list PoEList_Entry {
        type int32;
      }
    }
    container SFPList {
      leaf-list SFPList_Entry {
        type int32;
      }
    }
    container LAGList {
      leaf-list LAGList_Entry {
        type int32;
      }
    }
  }
  grouping DevicePortEntry {
    leaf DeviceID {
      type int32;
    }
    leaf PortNo {
      type int32;
    }
  }
  grouping DevicePortList {
    container List {
      list List_Entry {
        uses DevicePortEntry;
      }
    }
  }
  grouping DeviceTrunkEntry {
    leaf DeviceID {
      type int32;
    }
    leaf TrunkID {
      type int32;
    }
  }
  grouping DeviceTrunkList {
    container List {
      list List_Entry {
        uses DeviceTrunkEntry;
      }
    }
  }
  grouping DeviceInterfaceEntry {
    leaf Type {
      type InterfaceTypeOptions;
    }
    leaf DeviceID {
      type int32;
    }
    leaf PortNo {
      type int32;
    }
    leaf LAGNo {
      type int32;
    }
  }
  grouping DeviceInterfaceList {
    container List {
      list List_Entry {
        uses DeviceInterfaceEntry;
      }
    }
  }
  grouping TrunkingGroupMemberEntry {
    leaf LAGNo {
      type int32;
    }
    container EnableMemberList {
      uses DevicePortList;
    }
    container DisableMemberList {
      uses DevicePortList;
    }
  }
  grouping TrunkingMemberEntry {
    leaf LAGNo {
      type int32;
    }
    container MemberList {
      uses DevicePortList;
    }
  }
  grouping TrunkingGroupID {
    leaf LAGNo {
      type int32;
    }
  }
  grouping TrunkingLoadBalanceMode {
    leaf Mode {
      type TrunkingLoadBalanceModeOptions;
    }
  }
  grouping ACLIndexList {
    container List {
      leaf-list List_Entry {
        type int32;
      }
    }
  }
  grouping ACLUserDefinedRuleList {
    container List {
      list List_Entry {
        uses ACLUserDefinedRuleEntry;
      }
    }
  }
  grouping ACLUserDefinedRuleEntry {
    leaf Index {
      type int32;
    }
    leaf UniqueID {
      type string;
    }
    leaf DirectionType {
      type ACLDirectionTypeOptions;
    }
    leaf Type {
      type ACLRuleTypeOptions;
    }
    leaf SourceMAC {
      type string;
    }
    leaf SourceMACMask {
      type string;
    }
    leaf DestinationMAC {
      type string;
    }
    leaf DestinationMACMask {
      type string;
    }
    leaf EtherType {
      type int32;
    }
    leaf EtherTypeMask {
      type int32;
    }
    leaf SourceIPAddr {
      type string;
    }
    leaf SourceIPMask {
      type string;
    }
    leaf DestinationIPAddr {
      type string;
    }
    leaf DestinationIPMask {
      type string;
    }
    leaf IPProtocol {
      type int32;
    }
    leaf IPProtocolMask {
      type int32;
    }
    leaf L4SourcePort {
      type int32;
    }
    leaf L4SourcePortMask {
      type int32;
    }
    leaf L4DestinationPort {
      type int32;
    }
    leaf L4DestinationPortMask {
      type int32;
    }
    leaf VlanID {
      type int32;
    }
    container SourceInterface {
      uses ACLSourceInterfaceEntry;
    }
    container Action {
      uses ACLActionEntry;
    }
  }
  grouping ACLUserDefinedRuleRemovalList {
    container List {
      list List_Entry {
        uses ACLUserDefinedRuleRemovalEntry;
      }
    }
  }
  grouping ACLUserDefinedRuleRemovalEntry {
    leaf Index {
      type int32;
    }
    leaf UniqueID {
      type string;
    }
  }
  grouping ACLControlRuleEntry {
    leaf Type {
      type ACLRuleTypeOptions;
    }
    leaf Index {
      type int32;
    }
    choice Rule {
      container MACIPBindingRule {
        uses ACLMACIPBindingRuleEntry;
      }
      container SubnetBasedRule {
        uses ACLSubnetBasedRuleEntry;
      }
      container MACBasedRule {
        uses ACLMACBasedRuleEntry;
      }
      container SelectiveQinQRule {
        uses ACLSelectiveQinQRuleEntry;
      }
      container FlowMirrorRule {
        uses ACLFlowMirrorRuleEntry;
      }
      container MACCountingRule {
        uses ACLMACCountingRuleEntry;
      }
      container PTPMessageRule {
        uses ACLPTPMessageRuleEntry;
      }
    }
    container SourceInterface {
      uses ACLSourceInterfaceEntry;
    }
    container Action {
      uses ACLActionEntry;
    }
  }
  grouping ACLSourceInterfaceEntry {
    leaf Type {
      type InterfaceTypeOptions;
    }
    leaf VlanID {
      type int32;
    }
    container PortList {
      list PortList_Entry {
        uses DevicePortEntry;
      }
    }
    container LAGList {
      list LAGList_Entry {
        uses TrunkingGroupID;
      }
    }
  }
  grouping ACLActionEntry {
    leaf PacketCommand {
      type PacketCommandOptions;
    }
  }
  grouping ACLG8032RuleEntry {
    leaf RingID {
      type int32;
    }
    leaf VlanID {
      type int32;
    }
    leaf DestinationRingPort {
      type int32;
    }
  }
  grouping ACLMACIPBindingRuleEntry {
    leaf SourceMAC {
      type string;
    }
    leaf SourceIPAddr {
      type string;
    }
  }
  grouping ACLSubnetBasedRuleEntry {
    leaf SourceIPAddr {
      type string;
    }
    leaf SourceIPMask {
      type string;
    }
    leaf ModifyVlanID {
      type int32;
    }
  }
  grouping ACLMACBasedRuleEntry {
    leaf SourceMAC {
      type string;
    }
    leaf SourceMACMask {
      type string;
    }
    leaf ModifyVlanID {
      type int32;
    }
  }
  grouping ACLSelectiveQinQRuleEntry {
    leaf VlanFrom {
      type int32;
    }
    leaf VlanTo {
      type int32;
    }
  }
  grouping ACLFlowMirrorRuleEntry {
    leaf IsMirrorEnabled {
      type boolean;
    }
    container Flow {
      uses ACLUserDefinedRuleEntry;
    }
  }
  grouping ACLMACCountingRuleEntry {
    leaf CNCCounterIndex {
      type int32;
    }
    leaf SourceMAC {
      type string;
    }
  }
  grouping ACLPTPMessageRuleEntry {
    leaf EtherType {
      type int32;
    }
  }
  grouping CNCCountingEntry {
    leaf Type {
      type CNCCountingTypeOptions;
    }
    choice Entry {
      container MACAddressCountingEntry {
        uses CNCMACAddressCountingEntry;
      }
    }
  }
  grouping CNCMACAddressCountingEntry {
    container Address {
      uses MACAddress;
    }
  }
  grouping CNCCounter {
    leaf ByteCount {
      type uint64;
    }
    leaf PktCount {
      type uint64;
    }
  }
  grouping FDBAutoLearningEnable {
    leaf Enable {
      type boolean;
    }
  }
  grouping FDBIdentifyEntry {
    leaf VlanID {
      type int32;
    }
    leaf Address {
      type string;
    }
  }
  grouping FDBSecureBreachEntry {
    container Port {
      uses DevicePortEntry;
    }
    leaf Enable {
      type boolean;
    }
  }
  grouping FDBMACEntry {
    leaf InterfaceType {
      type InterfaceTypeOptions;
    }
    leaf IsStatic {
      type boolean;
    }
    leaf IsForward {
      type boolean;
    }
    leaf VlanID {
      type int32;
    }
    leaf Address {
      type string;
    }
    container Port {
      uses DevicePortEntry;
    }
    container Trunk {
      uses DeviceTrunkEntry;
    }
    container Multicast {
      uses FDBMulticastEntry;
    }
    leaf Action {
      type FDBEntryActionTypeOptions;
    }
  }
  grouping FDBDumpEntry {
    container List {
      list List_Entry {
        uses FDBMACEntry;
      }
    }
  }
  grouping FDBHashEntry {
    leaf LayerType {
      type FDBLayerTypeOptions;
    }
    leaf VlanID {
      type int32;
    }
    leaf Address {
      type string;
    }
  }
  grouping FDBAgingTime {
    leaf Time {
      type int32;
    }
  }
  grouping FDBFlushEntry {
    leaf InterfaceType {
      type InterfaceTypeOptions;
    }
    leaf IsUnicastDynamic {
      type boolean;
    }
    leaf IsUnicastAll {
      type boolean;
    }
    leaf IsMulticast {
      type boolean;
    }
    container VlanList {
      leaf-list VlanList_Entry {
        type int32;
      }
    }
    container PortList {
      uses DevicePortList;
    }
    container TrunkList {
      uses DeviceTrunkList;
    }
  }
  grouping FDBMulticastEntry {
    leaf EntryType {
      type MulticastEntryTypeOptions;
    }
    leaf VIDX {
      type int32;
    }
  }
  grouping FDBCounters {
    leaf NumberOfFreeEntries {
      type int32;
    }
    leaf NumberOfUsedEntries {
      type int32;
    }
    leaf NumberOfMacUnicastDynamicEntries {
      type int32;
    }
    leaf NumberOfMacUnicastStaticEntries {
      type int32;
    }
    leaf NumberOfMacMulticastDynamicEntries {
      type int32;
    }
    leaf NumberOfMacMulticastStaticEntries {
      type int32;
    }
    leaf NumberOfIpv4MulticastEntries {
      type int32;
    }
    leaf NumberOfIpv6MulticastEntries {
      type int32;
    }
  }
  grouping MirroringSessionEntry {
    leaf SourceType {
      type InterfaceTypeOptions;
    }
    container SourcePortList {
      list SourcePortList_Entry {
        uses MirroringSourcePortEntry;
      }
    }
    container SourceVlanList {
      list SourceVlanList_Entry {
        uses MirroringSourceVlanEntry;
      }
    }
    container DestinationPort {
      uses DevicePortEntry;
    }
    container RSPAN {
      uses MirroringRSPANEntry;
    }
  }
  grouping MirroringSourcePortEntry {
    leaf Direction {
      type MirroringDirectionTypeOptions;
    }
    container Port {
      uses DevicePortEntry;
    }
  }
  grouping MirroringSourceVlanEntry {
    leaf Direction {
      type MirroringDirectionTypeOptions;
    }
    leaf VlanID {
      type int32;
    }
  }
  grouping MirroringSessionList {
    container List {
      list List_Entry {
        uses MirroringSessionEntry;
      }
    }
  }
  grouping MirroringPolicyBased {
    leaf IsEnabled {
      type boolean;
    }
    container DestinationPort {
      uses DevicePortEntry;
    }
  }
  grouping MirroringRSPANEntry {
    leaf IsLocalEnabled {
      type boolean;
    }
    leaf IsRemoteEnabled {
      type boolean;
    }
    leaf AnalyzerVlanID {
      type int32;
    }
  }
  grouping MiscMACRegisterEntry {
    leaf Address {
      type uint32;
    }
    leaf Data {
      type uint32;
    }
  }
  grouping MiscSMIRegisterEntry {
    leaf PHYInterface {
      type uint32;
    }
    leaf PHYID {
      type uint32;
    }
    leaf Address {
      type uint32;
    }
    leaf Data {
      type uint32;
    }
  }
  grouping MiscXSMIRegisterEntry {
    leaf PHYInterface {
      type uint32;
    }
    leaf PHYID {
      type uint32;
    }
    leaf PHYDev {
      type uint32;
    }
    leaf Address {
      type uint32;
    }
    leaf Data {
      type uint32;
    }
  }
  grouping MiscRegisterData {
    leaf Data {
      type uint32;
    }
  }
  grouping MiscTemperature {
    leaf Temperature {
      type int32;
    }
  }
  grouping MiscPHYPortModel {
    leaf Interface {
      type string;
    }
    leaf Model {
      type string;
    }
  }
  grouping MiscModel {
    leaf Model {
      type string;
    }
  }
  grouping VlanID {
    leaf VlanID {
      type int32;
    }
  }
  grouping VlanList {
    container List {
      leaf-list List_Entry {
        type int32;
      }
    }
  }
  grouping VlanMemberTaggingList {
    leaf VlanID {
      type int32;
    }
    container List {
      list List_Entry {
        uses VlanMemeberTaggingEntry;
      }
    }
  }
  grouping VlanMemeberTaggingEntry {
    container Interface {
      uses DeviceInterfaceEntry;
    }
    leaf Command {
      type VlanTaggingCommandTypeOptions;
    }
  }
  grouping VlanDefaultVIDEntry {
    leaf VlanID {
      type int32;
    }
    container Interface {
      uses DeviceInterfaceEntry;
    }
  }
  grouping VlanAcceptFrameTypeEntry {
    container Interface {
      uses DeviceInterfaceEntry;
    }
    leaf Type {
      type VlanAcceptFrameTypeOptions;
    }
  }
  grouping VlanTPIDIndexEntry {
    container Interface {
      uses DeviceInterfaceEntry;
    }
    leaf Index {
      type int32;
    }
  }
  grouping VlanTPIDEntry {
    leaf Index {
      type int32;
    }
    leaf TPID {
      type int32;
    }
  }
  grouping VlanTPIDList {
    container List {
      list List_Entry {
        uses VlanTPIDEntry;
      }
    }
  }
  grouping VlanStatusEntry {
    leaf VlanID {
      type int32;
    }
    container UntaggedList {
      leaf-list UntaggedList_Entry {
        type int32;
      }
    }
    container TaggedList {
      leaf-list TaggedList_Entry {
        type int32;
      }
    }
    container ProviderList {
      leaf-list ProviderList_Entry {
        type int32;
      }
    }
    container CustomerList {
      leaf-list CustomerList_Entry {
        type int32;
      }
    }
  }
  grouping VlanStatusList {
    container List {
      list List_Entry {
        uses VlanStatusEntry;
      }
    }
  }
  grouping VlanFlushEntry {
    leaf IsFlushAll {
      type boolean;
    }
    leaf VlanID {
      type int32;
    }
  }
  grouping VlanTunnelEntry {
    container Interface {
      uses DeviceInterfaceEntry;
    }
    leaf IsEnabled {
      type boolean;
    }
  }
  grouping VlanProtocolClassID {
    leaf ClassID {
      type int32;
    }
  }
  grouping VlanProtocolClassEntry {
    leaf ClassID {
      type int32;
    }
    leaf EtherType {
      type int32;
    }
    leaf Encapsulation {
      type VlanProtocolBasedEncapsulationTypeOptions;
    }
  }
  grouping VlanProtocolEntry {
    container Interface {
      uses DeviceInterfaceEntry;
    }
    leaf ClassID {
      type int32;
    }
    leaf VlanID {
      type int32;
    }
  }
  grouping VlanTranslationEntry {
    container Interface {
      uses DeviceInterfaceEntry;
    }
    leaf IsEnabled {
      type boolean;
    }
  }
  grouping VlanTranslationMappingEntry {
    leaf SourceVlanID {
      type int32;
    }
    leaf TranslatedVlanID {
      type int32;
    }
  }
  grouping MulticastBridgeGroupEntry {
    container Identify {
      uses FDBIdentifyEntry;
    }
    container InterfaceList {
      list InterfaceList_Entry {
        uses DeviceInterfaceEntry;
      }
    }
  }
  grouping MulticastUnregisteredFloodingEntry {
    leaf VlanID {
      type int32;
    }
    container InterfaceList {
      list InterfaceList_Entry {
        uses DeviceInterfaceEntry;
      }
    }
  }
  grouping MulticastTableVlanFloodingEntry {
    leaf VlanID {
      type int32;
    }
    leaf VIDX {
      type int32;
    }
    container PortList {
      list PortList_Entry {
        uses DevicePortEntry;
      }
    }
  }
  grouping MulticastTableBridgeGroupEntry {
    leaf VlanID {
      type int32;
    }
    leaf VIDX {
      type int32;
    }
    leaf Address {
      type string;
    }
    container PortList {
      list PortList_Entry {
        uses DevicePortEntry;
      }
    }
  }
  grouping MulticastTable {
    container VlanFloodingList {
      list VlanFloodingList_Entry {
        uses MulticastTableVlanFloodingEntry;
      }
    }
    container BridgeGroupList {
      list BridgeGroupList_Entry {
        uses MulticastTableBridgeGroupEntry;
      }
    }
  }
  grouping PacketControlActionEntry {
    leaf Enable {
      type boolean;
    }
    leaf VlanID {
      type int32;
    }
    container Port {
      uses DevicePortEntry;
    }
  }
  grouping PacketControlGeneralStatusEntry {
    leaf Protocol {
      type PacketControlProtocolTypeOptions;
    }
    leaf IsEnabled {
      type boolean;
    }
    leaf PacketCommand {
      type PacketCommandOptions;
    }
  }
  grouping PacketControlInterfaceStatusEntry {
    leaf Protocol {
      type PacketControlProtocolTypeOptions;
    }
    leaf Type {
      type InterfaceTypeOptions;
    }
    container EnabledList {
      leaf-list EnabledList_Entry {
        type int32;
      }
    }
    leaf PacketCommand {
      type PacketCommandOptions;
    }
  }
  grouping PacketControlStatusList {
    container GeneralList {
      list GeneralList_Entry {
        uses PacketControlGeneralStatusEntry;
      }
    }
    container InterfaceList {
      list InterfaceList_Entry {
        uses PacketControlInterfaceStatusEntry;
      }
    }
  }
  grouping PolicerStormCountingEnableEntry {
    leaf IsEnable {
      type boolean;
    }
    container Port {
      uses DevicePortEntry;
    }
  }
  grouping PolicerStormCountingCounterEntry {
    leaf UnknownUnicastByteCount {
      type uint64;
    }
    leaf UnknownUnicastPktCount {
      type uint64;
    }
    leaf MulticastByteCount {
      type uint64;
    }
    leaf MulticastPktCount {
      type uint64;
    }
    leaf BroadcastByteCount {
      type uint64;
    }
    leaf BroadcastPktCount {
      type uint64;
    }
  }
  grouping PortEnableEntry {
    container Port {
      uses DevicePortEntry;
    }
    leaf Enable {
      type boolean;
    }
    leaf Speed {
      type PortSpeedDuplexOptions;
    }
  }
  grouping PortSpeedDuplexEntry {
    container Port {
      uses DevicePortEntry;
    }
    leaf Speed {
      type PortSpeedDuplexOptions;
    }
  }
  grouping PortSpeedDuplexList {
    container List {
      list List_Entry {
        uses PortSpeedDuplexEntry;
      }
    }
  }
  grouping PortFlowControlEntry {
    container Port {
      uses DevicePortEntry;
    }
    leaf Enable {
      type boolean;
    }
  }
  grouping PortEEEEntry {
    container Port {
      uses DevicePortEntry;
    }
    leaf Enable {
      type boolean;
    }
  }
  grouping PortCounterEntry {
    container Port {
      uses DevicePortEntry;
    }
    leaf GoodOctetsRecv {
      type uint64;
    }
    leaf BadOctetsRecv {
      type uint64;
    }
    leaf MACTransmitErr {
      type uint64;
    }
    leaf GoodPktsRecv {
      type uint64;
    }
    leaf BadPktsRecv {
      type uint64;
    }
    leaf BrdcPktsRecv {
      type uint64;
    }
    leaf McPktsRecv {
      type uint64;
    }
    leaf Pkts_64Octets {
      type uint64;
    }
    leaf Pkts_65To_127Octets {
      type uint64;
    }
    leaf Pkts_128To_255Octets {
      type uint64;
    }
    leaf Pkts_256To_511Octets {
      type uint64;
    }
    leaf Pkts_512To_1023Octets {
      type uint64;
    }
    leaf Pkts_1024ToMaxOctets {
      type uint64;
    }
    leaf GoodOctetsSent {
      type uint64;
    }
    leaf GoodPktsSent {
      type uint64;
    }
    leaf ExcessiveCollisions {
      type uint64;
    }
    leaf McPktsSent {
      type uint64;
    }
    leaf BrdcPktsSent {
      type uint64;
    }
    leaf UnrecogMACCntrRecv {
      type uint64;
    }
    leaf FCSent {
      type uint64;
    }
    leaf GoodFCRecv {
      type uint64;
    }
    leaf DropEvents {
      type uint64;
    }
    leaf UndersizePkts {
      type uint64;
    }
    leaf FragmentsPkts {
      type uint64;
    }
    leaf OversizePkts {
      type uint64;
    }
    leaf JabberPkts {
      type uint64;
    }
    leaf MACRecvError {
      type uint64;
    }
    leaf BadCrc {
      type uint64;
    }
    leaf Collisions {
      type uint64;
    }
    leaf LateCollisions {
      type uint64;
    }
    leaf BadFcRecv {
      type uint64;
    }
    leaf UcPktsRecv {
      type uint64;
    }
    leaf UcPktsSent {
      type uint64;
    }
    leaf MultiplePktsSent {
      type uint64;
    }
    leaf DeferredPktsSent {
      type uint64;
    }
  }
  grouping PortCounterList {
    container List {
      list List_Entry {
        uses PortCounterEntry;
      }
    }
  }
  grouping PortIsolationEntry {
    container Port {
      uses DevicePortEntry;
    }
    container OutgoingList {
      list OutgoingList_Entry {
        uses DevicePortEntry;
      }
    }
  }
  grouping PortIsolationList {
    container List {
      list List_Entry {
        uses PortIsolationEntry;
      }
    }
  }
  grouping PortIPGSize {
    leaf Size {
      type int32;
    }
  }
  grouping PortFaultStatusEntry {
    leaf IsRxFault {
      type boolean;
    }
    leaf IsTxFault {
      type boolean;
    }
  }
  grouping PortStatusEntry {
    container Port {
      uses DevicePortEntry;
    }
    leaf IsEnabled {
      type boolean;
    }
    leaf IsLinkUp {
      type boolean;
    }
    leaf IsFlowControlEnabled {
      type boolean;
    }
    leaf LinkSpeed {
      type PortSpeedDuplexOptions;
    }
    leaf EEEActive {
      type boolean;
    }
    leaf PMState {
      type string;
    }
  }
  grouping PTPToD {
    leaf Sec {
      type uint64;
    }
    leaf Ns {
      type uint32;
    }
  }
  grouping PTPToDFrequency {
    leaf FractionalNs {
      type uint32;
    }
  }
  grouping PTPQueueInfo {
    leaf Sec {
      type uint64;
    }
    leaf Ns {
      type uint32;
    }
  }
  grouping PTPMessageInfo {
    container Port {
      uses DevicePortEntry;
    }
    leaf SeqID {
      type uint32;
    }
    leaf MessageType {
      type uint32;
    }
    leaf QueueNo {
      type uint32;
    }
  }
  grouping PTPLinkDelay {
    container Port {
      uses DevicePortEntry;
    }
    leaf Delay {
      type int32;
    }
  }
  grouping PTPPortDelay {
    container Port {
      uses DevicePortEntry;
    }
    leaf Direction {
      type PTPPortDelayTypeOptions;
    }
    leaf Delay {
      type int32;
    }
  }
  grouping PTPMode {
    container Port {
      uses DevicePortEntry;
    }
    leaf DomainIndex {
      type uint32;
    }
    leaf DomainNumber {
      type uint32;
    }
    leaf Mode {
      type PTPModeTypeOptions;
    }
  }
  grouping PTPSyncE {
    container Port {
      uses DevicePortEntry;
    }
    leaf IsEnable {
      type boolean;
    }
    leaf Speed {
      type PortSpeedDuplexOptions;
    }
    leaf ClockSelect {
      type PTPSyncERecoveryClockSelectTypeOptions;
    }
  }
  grouping QoSPortProfileEntry {
    container Port {
      uses DevicePortEntry;
    }
    leaf Mode {
      type QoSTrustModeOptions;
    }
  }
  grouping QoSPortProfileList {
    container List {
      list List_Entry {
        uses QoSPortProfileEntry;
      }
    }
  }
  grouping QoSPortQueueList {
    container List {
      list List_Entry {
        uses QoSPortQueueEntry;
      }
    }
  }
  grouping QoSPortQueueEntry {
    leaf QueueNo {
      type int32;
    }
    leaf Ratio {
      type int32;
    }
    leaf Scheduler {
      type QoSSchedulerTypeOptions;
    }
  }
  grouping QoSCoSProfile {
    leaf CoSNo {
      type int32;
    }
    leaf QueueNo {
      type int32;
    }
  }
  grouping QoSCoSProfileList {
    container CoSList {
      list CoSList_Entry {
        uses QoSCoSProfile;
      }
    }
  }
  grouping QoSDSCPProfile {
    leaf DSCPNo {
      type int32;
    }
    leaf QueueNo {
      type int32;
    }
  }
  grouping QoSDSCPProfileList {
    container DSCPList {
      list DSCPList_Entry {
        uses QoSDSCPProfile;
      }
    }
  }
  grouping RateLimitingIngressEntry {
    container FilterTypes {
      leaf-list FilterTypes_Entry {
        type RateLimitingIngressFilterTypeOptions;
      }
    }
    container Port {
      uses DevicePortEntry;
    }
    leaf Rate {
      type int32;
    }
  }
  grouping RateLimitingIngressList {
    container List {
      list List_Entry {
        uses RateLimitingIngressEntry;
      }
    }
  }
  grouping RateLimitingEgressEntry {
    container Port {
      uses DevicePortEntry;
    }
    leaf Rate {
      type int32;
    }
  }
  grouping RateLimitingEgressList {
    container List {
      list List_Entry {
        uses RateLimitingEgressEntry;
      }
    }
  }
  grouping STPID {
    leaf ID {
      type int32;
    }
    leaf Proto {
      type STPProtocolTypeOptions;
    }
  }
  grouping STPPortState {
    leaf ID {
      type int32;
    }
    container IdentifyNo {
      uses DeviceInterfaceEntry;
    }
    leaf State {
      type STPPortStateTypeOptions;
    }
    leaf InActive {
      type boolean;
    }
    leaf Proto {
      type STPProtocolTypeOptions;
    }
  }
  grouping STPVlanBinding {
    leaf ID {
      type int32;
    }
    leaf Proto {
      type STPProtocolTypeOptions;
    }
    container VlanList {
      leaf-list VlanList_Entry {
        type int32;
      }
    }
  }
  grouping STPIDState {
    leaf ID {
      type int32;
    }
    leaf State {
      type STPPortStateTypeOptions;
    }
    leaf Proto {
      type STPProtocolTypeOptions;
    }
  }
  rpc intri-cpss-Device-RunCPSSInit {
  }
  rpc intri-cpss-Device-GetArchitecture {
    output {
      uses DeviceArchitecture;
    }
  }
  rpc intri-cpss-Trunking-SetGroup {
    input {
      uses TrunkingGroupMemberEntry;
    }
  }
  rpc intri-cpss-Trunking-AddGroup {
    input {
      uses TrunkingMemberEntry;
    }
  }
  rpc intri-cpss-Trunking-DeleteGroup {
    input {
      uses TrunkingMemberEntry;
    }
  }
  rpc intri-cpss-Trunking-SetLoadBalanceMode {
    input {
      uses TrunkingLoadBalanceMode;
    }
  }
  rpc intri-cpss-Trunking-GetLoadBalanceMode {
    output {
      uses TrunkingLoadBalanceMode;
    }
  }
  rpc intri-cpss-Trunking-GetGroup {
    input {
      uses TrunkingGroupID;
    }
    output {
      uses TrunkingGroupMemberEntry;
    }
  }
  rpc intri-cpss-ACL-RunClearAllRules {
  }
  rpc intri-cpss-ACL-UpdateControlRule {
    input {
      uses ACLControlRuleEntry;
    }
  }
  rpc intri-cpss-ACL-AddControlRule {
    input {
      uses ACLControlRuleEntry;
    }
  }
  rpc intri-cpss-ACL-DeleteControlRule {
    input {
      uses ACLControlRuleEntry;
    }
  }
  rpc intri-cpss-ACL-RunClearControlRule {
    input {
      uses ACLControlRuleEntry;
    }
  }
  rpc intri-cpss-ACL-AddUserDefinedRules {
    input {
      uses ACLUserDefinedRuleList;
    }
  }
  rpc intri-cpss-ACL-DeleteUserDefinedRules {
    input {
      uses ACLUserDefinedRuleRemovalList;
    }
  }
  rpc intri-cpss-ACL-RunClearAllUserDefinedRules {
  }
  rpc intri-cpss-CNC-AddCounting {
    input {
      uses CNCCountingEntry;
    }
  }
  rpc intri-cpss-CNC-DeleteCounting {
    input {
      uses CNCCountingEntry;
    }
  }
  rpc intri-cpss-CNC-GetCounter {
    input {
      uses CNCCountingEntry;
    }
    output {
      uses CNCCounter;
    }
  }
  rpc intri-cpss-FDB-SetAutoLearnEnable {
    input {
      uses FDBAutoLearningEnable;
    }
  }
  rpc intri-cpss-FDB-SetEntry {
    input {
      uses FDBMACEntry;
    }
  }
  rpc intri-cpss-FDB-DeleteEntry {
    input {
      uses FDBMACEntry;
    }
  }
  rpc intri-cpss-FDB-SetAgingTime {
    input {
      uses FDBAgingTime;
    }
  }
  rpc intri-cpss-FDB-GetAgingTime {
    output {
      uses FDBAgingTime;
    }
  }
  rpc intri-cpss-FDB-SetSecureBreachNaPortEnable {
    input {
      uses FDBSecureBreachEntry;
    }
  }
  rpc intri-cpss-FDB-GetSecureBreachNaPortEnable {
    input {
      uses DevicePortEntry;
    }
    output {
      uses Enabled;
    }
  }
  rpc intri-cpss-FDB-GetCounter {
    output {
      uses FDBCounters;
    }
  }
  rpc intri-cpss-FDB-RunFlush {
    input {
      uses FDBFlushEntry;
    }
  }
  rpc intri-cpss-FDB-RunDump {
    output {
      uses FDBDumpEntry;
    }
  }
  rpc intri-cpss-Mirroring-RunClearAll {
  }
  rpc intri-cpss-Mirroring-SetSessions {
    input {
      uses MirroringSessionList;
    }
  }
  rpc intri-cpss-Mirroring-SetPolicyBased {
    input {
      uses MirroringPolicyBased;
    }
  }
  rpc intri-cpss-Misc-RunMACRegisterWrite {
    input {
      uses MiscMACRegisterEntry;
    }
  }
  rpc intri-cpss-Misc-RunMACRegisterRead {
    input {
      uses MiscMACRegisterEntry;
    }
    output {
      uses MiscRegisterData;
    }
  }
  rpc intri-cpss-Misc-RunSMIRegisterWrite {
    input {
      uses MiscSMIRegisterEntry;
    }
  }
  rpc intri-cpss-Misc-RunSMIRegisterRead {
    input {
      uses MiscSMIRegisterEntry;
    }
    output {
      uses MiscRegisterData;
    }
  }
  rpc intri-cpss-Misc-RunXSMIRegisterWrite {
    input {
      uses MiscXSMIRegisterEntry;
    }
  }
  rpc intri-cpss-Misc-RunXSMIRegisterRead {
    input {
      uses MiscXSMIRegisterEntry;
    }
    output {
      uses MiscRegisterData;
    }
  }
  rpc intri-cpss-Misc-GetCPUTemperature {
    output {
      uses MiscTemperature;
    }
  }
  rpc intri-cpss-Misc-GetMACTemperature {
    output {
      uses MiscTemperature;
    }
  }
  rpc intri-cpss-Misc-GetPHYPortTemperature {
    input {
      uses DevicePortEntry;
    }
    output {
      uses MiscTemperature;
    }
  }
  rpc intri-cpss-Misc-GetCPUModel {
    output {
      uses MiscModel;
    }
  }
  rpc intri-cpss-Misc-GetPHYPortModel {
    input {
      uses DevicePortEntry;
    }
    output {
      uses MiscPHYPortModel;
    }
  }
  rpc intri-cpss-Vlan-AddGroup {
    input {
      uses VlanID;
    }
  }
  rpc intri-cpss-Vlan-DeleteGroup {
    input {
      uses VlanID;
    }
  }
  rpc intri-cpss-Vlan-AddMember {
    input {
      uses VlanMemberTaggingList;
    }
  }
  rpc intri-cpss-Vlan-DeleteMember {
    input {
      uses VlanMemberTaggingList;
    }
  }
  rpc intri-cpss-Vlan-UpdateAcceptFrameType {
    input {
      uses VlanAcceptFrameTypeEntry;
    }
  }
  rpc intri-cpss-Vlan-GetAcceptFrameType {
    input {
      uses DeviceInterfaceEntry;
    }
    output {
      uses VlanAcceptFrameTypeEntry;
    }
  }
  rpc intri-cpss-Vlan-UpdateDefaultVID {
    input {
      uses VlanDefaultVIDEntry;
    }
  }
  rpc intri-cpss-Vlan-GetDefaultVID {
    input {
      uses DeviceInterfaceEntry;
    }
    output {
      uses VlanID;
    }
  }
  rpc intri-cpss-Vlan-RunFlush {
  }
  rpc intri-cpss-Vlan-GetStatus {
    output {
      uses VlanStatusList;
    }
  }
  rpc intri-cpss-Vlan-UpdateTPIDEntry {
    input {
      uses VlanTPIDEntry;
    }
  }
  rpc intri-cpss-Vlan-DumpTPIDTable {
    output {
      uses VlanTPIDList;
    }
  }
  rpc intri-cpss-Vlan-UpdateTPIDIndex {
    input {
      uses VlanTPIDIndexEntry;
    }
  }
  rpc intri-cpss-Vlan-GetTPIDIndex {
    input {
      uses DeviceInterfaceEntry;
    }
    output {
      uses VlanTPIDIndexEntry;
    }
  }
  rpc intri-cpss-Vlan-RunClearTPIDIndex {
    input {
      uses DeviceInterfaceEntry;
    }
  }
  rpc intri-cpss-Vlan-SetTunnelEnable {
    input {
      uses VlanTunnelEntry;
    }
  }
  rpc intri-cpss-Vlan-GetTunnelEnable {
    input {
      uses DeviceInterfaceEntry;
    }
    output {
      uses Enabled;
    }
  }
  rpc intri-cpss-Vlan-UpdateProtocolClass {
    input {
      uses VlanProtocolClassEntry;
    }
  }
  rpc intri-cpss-Vlan-GetProtocolClass {
    input {
      uses VlanProtocolClassID;
    }
    output {
      uses VlanProtocolClassEntry;
    }
  }
  rpc intri-cpss-Vlan-RunClearProtocolClass {
    input {
      uses VlanProtocolClassID;
    }
  }
  rpc intri-cpss-Vlan-UpdateProtocol {
    input {
      uses VlanProtocolEntry;
    }
  }
  rpc intri-cpss-Vlan-GetProtocol {
    input {
      uses VlanProtocolEntry;
    }
    output {
      uses VlanProtocolEntry;
    }
  }
  rpc intri-cpss-Vlan-RunClearProtocol {
    input {
      uses VlanProtocolEntry;
    }
  }
  rpc intri-cpss-Vlan-UpdateTranslationEnable {
    input {
      uses VlanTranslationEntry;
    }
  }
  rpc intri-cpss-Vlan-GetTranslationEnable {
    input {
      uses DeviceInterfaceEntry;
    }
    output {
      uses Enabled;
    }
  }
  rpc intri-cpss-Vlan-UpdateTranslationMapping {
    input {
      uses VlanTranslationMappingEntry;
    }
  }
  rpc intri-cpss-Vlan-GetTranslationMapping {
    input {
      uses VlanID;
    }
    output {
      uses VlanID;
    }
  }
  rpc intri-cpss-Vlan-RunClearTranslationMapping {
    input {
      uses VlanID;
    }
  }
  rpc intri-cpss-Multicast-SetBridgeGroup {
    input {
      uses MulticastBridgeGroupEntry;
    }
  }
  rpc intri-cpss-Multicast-DeleteBridgeGroup {
    input {
      uses FDBIdentifyEntry;
    }
  }
  rpc intri-cpss-Multicast-SetUnregisteredFlooding {
    input {
      uses MulticastUnregisteredFloodingEntry;
    }
  }
  rpc intri-cpss-Multicast-RunClearUnregisteredFlooding {
    input {
      uses VlanID;
    }
  }
  rpc intri-cpss-Multicast-RunDump {
    output {
      uses MulticastTable;
    }
  }
  rpc intri-cpss-Multicast-RunFlush {
  }
  rpc intri-cpss-PacketControl-UpdateSTPControl {
    input {
      uses PacketControlActionEntry;
    }
  }
  rpc intri-cpss-PacketControl-UpdateLACPControl {
    input {
      uses PacketControlActionEntry;
    }
  }
  rpc intri-cpss-PacketControl-UpdateDot1XControl {
    input {
      uses PacketControlActionEntry;
    }
  }
  rpc intri-cpss-PacketControl-UpdateLoopControl {
    input {
      uses PacketControlActionEntry;
    }
  }
  rpc intri-cpss-PacketControl-UpdateDHCPv4DiscoverControl {
    input {
      uses PacketControlActionEntry;
    }
  }
  rpc intri-cpss-PacketControl-UpdateDHCPv4BroadcastOfferControl {
    input {
      uses PacketControlActionEntry;
    }
  }
  rpc intri-cpss-PacketControl-UpdateDHCPv4UDPDestination68Control {
    input {
      uses PacketControlActionEntry;
    }
  }
  rpc intri-cpss-PacketControl-UpdateDHCPv4UDPDestination67Control {
    input {
      uses PacketControlActionEntry;
    }
  }
  rpc intri-cpss-PacketControl-UpdateARPControl {
    input {
      uses PacketControlActionEntry;
    }
  }
  rpc intri-cpss-PacketControl-UpdateIGMPVlanControl {
    input {
      uses PacketControlActionEntry;
    }
  }
  rpc intri-cpss-PacketControl-UpdateMLDVlanControl {
    input {
      uses PacketControlActionEntry;
    }
  }
  rpc intri-cpss-PacketControl-UpdateGVRPControl {
    input {
      uses PacketControlActionEntry;
    }
  }
  rpc intri-cpss-PacketControl-GetStatus {
    output {
      uses PacketControlStatusList;
    }
  }
  rpc intri-cpss-Policer-SetStormCountingEnable {
    input {
      uses PolicerStormCountingEnableEntry;
    }
  }
  rpc intri-cpss-Policer-GetStormCountingEnable {
    input {
      uses DevicePortEntry;
    }
    output {
      uses PolicerStormCountingEnableEntry;
    }
  }
  rpc intri-cpss-Policer-GetStormCountingCounter {
    input {
      uses DevicePortEntry;
    }
    output {
      uses PolicerStormCountingCounterEntry;
    }
  }
  rpc intri-cpss-Port-SetEnable {
    input {
      uses PortEnableEntry;
    }
  }
  rpc intri-cpss-Port-GetEnable {
    input {
      uses DevicePortEntry;
    }
    output {
      uses PortEnableEntry;
    }
  }
  rpc intri-cpss-Port-SetSpeedDuplex {
    input {
      uses PortSpeedDuplexEntry;
    }
  }
  rpc intri-cpss-Port-GetSpeedDuplex {
    input {
      uses DevicePortEntry;
    }
    output {
      uses PortSpeedDuplexEntry;
    }
  }
  rpc intri-cpss-Port-SetFlowControl {
    input {
      uses PortFlowControlEntry;
    }
  }
  rpc intri-cpss-Port-GetFlowControl {
    input {
      uses DevicePortEntry;
    }
    output {
      uses PortFlowControlEntry;
    }
  }
  rpc intri-cpss-Port-SetEnableEEE {
    input {
      uses PortEEEEntry;
    }
  }
  rpc intri-cpss-Port-GetEnableEEE {
    input {
      uses DevicePortEntry;
    }
    output {
      uses PortEEEEntry;
    }
  }
  rpc intri-cpss-Port-GetCounter {
    input {
      uses DevicePortEntry;
    }
    output {
      uses PortCounterEntry;
    }
  }
  rpc intri-cpss-Port-RunClearCounter {
    input {
      uses DevicePortEntry;
    }
  }
  rpc intri-cpss-Port-SetIsolation {
    input {
      uses PortIsolationList;
    }
  }
  rpc intri-cpss-Port-GetIsolation {
    output {
      uses PortIsolationList;
    }
  }
  rpc intri-cpss-Port-GetIPG {
    output {
      uses PortIPGSize;
    }
  }
  rpc intri-cpss-Port-GetFaultStatus {
    input {
      uses DevicePortEntry;
    }
    output {
      uses PortFaultStatusEntry;
    }
  }
  rpc intri-cpss-Port-GetStatus {
    input {
      uses DevicePortEntry;
    }
    output {
      uses PortStatusEntry;
    }
  }
  rpc intri-cpss-PTP-SetMode {
    input {
      uses PTPMode;
    }
  }
  rpc intri-cpss-PTP-GetIngrTS {
    input {
      uses PTPMessageInfo;
    }
    output {
      uses PTPQueueInfo;
    }
  }
  rpc intri-cpss-PTP-GetEgrTS {
    input {
      uses PTPMessageInfo;
    }
    output {
      uses PTPQueueInfo;
    }
  }
  rpc intri-cpss-PTP-SetLinkDelay {
    input {
      uses PTPLinkDelay;
    }
  }
  rpc intri-cpss-PTP-GetLinkDelay {
    input {
      uses PTPLinkDelay;
    }
    output {
      uses PTPLinkDelay;
    }
  }
  rpc intri-cpss-PTP-SetEnableSyncE {
    input {
      uses PTPSyncE;
    }
  }
  rpc intri-cpss-PTP-SetToD {
    input {
      uses PTPToD;
    }
  }
  rpc intri-cpss-PTP-GetToD {
    output {
      uses PTPToD;
    }
  }
  rpc intri-cpss-PTP-SetToDFrequency {
    input {
      uses PTPToDFrequency;
    }
  }
  rpc intri-cpss-PTP-SetPortDelay {
    input {
      uses PTPPortDelay;
    }
  }
  rpc intri-cpss-PTP-GetPortDelay {
    input {
      uses PTPPortDelay;
    }
    output {
      uses PTPPortDelay;
    }
  }
  rpc intri-cpss-QoS-SetQoSPortProfile {
    input {
      uses QoSPortProfileList;
    }
  }
  rpc intri-cpss-QoS-GetQoSPortProfile {
    output {
      uses QoSPortProfileList;
    }
  }
  rpc intri-cpss-QoS-SetQoSCoSProfile {
    input {
      uses QoSCoSProfileList;
    }
  }
  rpc intri-cpss-QoS-GetQoSCoSProfile {
    output {
      uses QoSCoSProfileList;
    }
  }
  rpc intri-cpss-QoS-SetQoSDSCPProfile {
    input {
      uses QoSDSCPProfileList;
    }
  }
  rpc intri-cpss-QoS-GetQoSDSCPProfile {
    output {
      uses QoSDSCPProfileList;
    }
  }
  rpc intri-cpss-QoS-SetQoSQueueProfile {
    input {
      uses QoSPortQueueList;
    }
  }
  rpc intri-cpss-QoS-GetQoSQueueProfile {
    output {
      uses QoSPortQueueList;
    }
  }
  rpc intri-cpss-RateLimiting-SetIngress {
    input {
      uses RateLimitingIngressList;
    }
  }
  rpc intri-cpss-RateLimiting-GetIngress {
    output {
      uses RateLimitingIngressList;
    }
  }
  rpc intri-cpss-RateLimiting-SetEgress {
    input {
      uses RateLimitingEgressList;
    }
  }
  rpc intri-cpss-RateLimiting-GetEgress {
    output {
      uses RateLimitingEgressList;
    }
  }
  rpc intri-cpss-STP-SetPortState {
    input {
      uses STPPortState;
    }
  }
  rpc intri-cpss-STP-GetPortState {
    input {
      uses STPPortState;
    }
    output {
      uses STPIDState;
    }
  }
  rpc intri-cpss-STP-SetVlanBinding {
    input {
      uses STPVlanBinding;
    }
  }
  rpc intri-cpss-STP-GetVlanBinding {
    input {
      uses STPID;
    }
    output {
      uses VlanList;
    }
  }
  rpc intri-cpss-STP-RunClearVlanBinding {
    input {
      uses STPVlanBinding;
    }
  }
}
