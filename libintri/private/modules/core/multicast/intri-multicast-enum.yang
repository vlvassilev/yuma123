submodule intri-multicast-enum {
  belongs-to "intri-multicast" {
    prefix "intri-multicast-enum";
  }
  revision 2022-06-14 {
    description "Build date.";
  }
  // core/multicast/common.proto
  typedef RouterDetectionTypeOptions {
    type enumeration {
      enum ROUTER_DETECTION_TYPE_QUERY_MESSAGE {
        description "[Query Message]";
        value 0;
      }
    }
  }
  // core/multicast/common.proto
  typedef ProtocolTypeOptions {
    type enumeration {
      enum PROTOCOL_TYPE_NONE {
        description "[NONE]";
        value 0;
      }
      enum PROTOCOL_TYPE_IGMP {
        description "[IGMP]";
        value 1;
      }
      enum PROTOCOL_TYPE_MLD {
        description "[MLD]";
        value 2;
      }
      enum PROTOCOL_TYPE_BOTH {
        description "[BOTH]";
        value 3;
      }
    }
  }
  // core/multicast/common.proto
  typedef RouterStatusTypeOptions {
    type enumeration {
      enum ROUTER_STATUS_TYPE_DISABLED {
        description "[Disabled]";
        value 0;
      }
      enum ROUTER_STATUS_TYPE_DYNAMIC {
        description "[Dynamic]";
        value 1;
      }
      enum ROUTER_STATUS_TYPE_STATIC {
        description "[Static]";
        value 2;
      }
      enum ROUTER_STATUS_TYPE_BOTH {
        description "[Both]";
        value 3;
      }
    }
  }
  // core/multicast/common.proto
  typedef VersionTypeOptions {
    type enumeration {
      enum VERSION_TYPE_IGMP_V1 {
        description "[IGMP V1]";
        value 0;
      }
      enum VERSION_TYPE_IGMP_V2 {
        description "[IGMP V2]";
        value 1;
      }
      enum VERSION_TYPE_IGMP_V3 {
        description "[IGMP V3]";
        value 2;
      }
      enum VERSION_TYPE_MLD_V1 {
        description "[MLD V1]";
        value 3;
      }
      enum VERSION_TYPE_MLD_V2 {
        description "[MLD V2]";
        value 4;
      }
      enum VERSION_TYPE_DISABLED {
        description "[Disabled]";
        value 5;
      }
    }
  }
  // core/multicast/common.proto
  typedef StaticTypeOptions {
    type enumeration {
      enum STATIC_TYPE_L2 {
        description "[L2]";
        value 0;
      }
      enum STATIC_TYPE_L3 {
        description "[L3]";
        value 1;
      }
    }
  }
}
