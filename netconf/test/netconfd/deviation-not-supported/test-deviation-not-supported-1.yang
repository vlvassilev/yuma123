module test-deviation-not-supported-1 {
	yang-version 1.1;
	namespace "urn:labn:params:xml:ns:yang:test-deviation-not-supported-1";
	prefix dev1;

	organization "";
	contact	"";
	description
		"Add an internal deviation to ensure that it is applied.";

	revision 2020-07-28 {
		reference "";
	}

	container top {
		leaf supported-value {
			type int8;
			description
				"An integer value";
		}

		leaf unsupported-value {
			type int8;
			description
				"Another integer value";
		}
		description "Two integer values";
	}

	deviation /dev1:top/dev1:unsupported-value {
		deviate not-supported;
	}
}
