// Code generated by protoc-gen-yang. DO NOT EDIT.


/* ****************************************************************************************************
 * Import Path : "github.com/Intrising/intri-type/core/stormcontrol"                                  *
 * Dir Path    : github.com/Intrising/intri-type/core/stormcontrol                                    *
 * Go Package  : stormcontrol                                                                         *
 * Files       : 2                                                                                    *
 **************************************************************************************************** */
module intri-stormcontrol {

  namespace "intri:intri-stormcontrol";

  prefix "intri-stormcontrol";

  organization "Intrising Inc.";

  contact "intrising@intrising.com.tw";

  revision 2022-06-23 {
    description "Build date.";
  }

  import intri-device {
    prefix intri-device;
  }
  import intri-empty {
    prefix intri-empty;
  }
  import intri-common {
    prefix intri-common;
  }


  /* **************************************************************************************************
   * Enums       : 3                                                                                  *
   ************************************************************************************************** */
  /* core/stormcontrol/stormcontrol.proto */
  typedef StormControlActionTypeOptions {
    type enumeration {
      enum STORM_CONTROL_ACTION_TYPE_SHUTDOWN {
        description "[Shutdown] the port interface will be shutdown when the percent of the outputed packet is over the max level";
        value 0;
      }
      enum STORM_CONTROL_ACTION_TYPE_BLOCKING {
        description "[Blocking] the port interface will be blocking when the percent of the outputed packet is over the max level";
        value 1;
      }
    }
  }
  /* core/stormcontrol/stormcontrol.proto */
  typedef StormControlSuppressionTypeOptions {
    type enumeration {
      enum STORM_CONTROL_SUPPRESSION_TYPE_BROADCAST {
        description "[Broadcast] counter forwards broadcast bits/packets per second of lading as the standard";
        value 0;
      }
      enum STORM_CONTROL_SUPPRESSION_TYPE_MULTICAST {
        description "[Multicast] counter forwards multicast bits/packets per second of lading as the standard";
        value 1;
      }
      enum STORM_CONTROL_SUPPRESSION_TYPE_UNKNOWN_UNICAST {
        description "[Unknown Unicast] counter forwards unknown unicast bits/packets per second of lading as the standard";
        value 2;
      }
    }
  }
  /* core/stormcontrol/stormcontrol.proto */
  typedef StormControlSuppressionUnitTypeOptions {
    type enumeration {
      enum STORM_CONTROL_SUPPRESSION_TYPE_BITS_PER_SECOND {
        description "[bits/sec.] counter bits per secound";
        value 0;
      }
      enum STORM_CONTROL_SUPPRESSION_TYPE_PACKETS_PER_SECOND {
        description "[packets/sec.] counter packets per secound";
        value 1;
      }
    }
  }


  /* **************************************************************************************************
   * Msgs        : 4                                                                                  *
   ************************************************************************************************** */
  /* core/stormcontrol/stormcontrol.proto */
  grouping SuppressionConfigEntry {
    leaf SuppressionOption {
      type StormControlSuppressionTypeOptions;
    }
    leaf IsEnable {
      type boolean;
    }
    leaf ActionOption {
      type StormControlActionTypeOptions;
    }
    leaf UnitOption {
      type StormControlSuppressionUnitTypeOptions;
    }
    leaf BpsUpperThreshold {
      type uint64;
    }
    leaf PpsUpperThreshold {
      type uint64;
    }
  }
  /* core/stormcontrol/stormcontrol.proto */
  grouping PortConfigEntry {
    container IdentifyNo {
      uses intri-device:InterfaceIdentify;
    }
    leaf IsEnable {
      type boolean;
    }
    container SuppressionList {
      list SuppressionList_Entry {
        uses SuppressionConfigEntry;
      }
    }
  }
  /* core/stormcontrol/stormcontrol.proto */
  grouping PortConfig {
    container List {
      list List_Entry {
        uses PortConfigEntry;
      }
    }
  }
  /* core/stormcontrol/stormcontrol.proto */
  grouping Config {
    leaf IsEnable {
      type boolean;
    }
    container PortConfig {
      uses PortConfig;
    }
  }


  /* **************************************************************************************************
   * Services    : 1                                                                                  *
   ************************************************************************************************** */

  /* **************************************************************************************************
   * Service     : StormControl                                                                       *
   * Methods     : 6                                                                                  *
   ************************************************************************************************** */
  /* core/stormcontrol/service.proto */
  rpc intri-stormcontrol-GetConfig {
    output  {
      uses Config;
    }
  }
  /* core/stormcontrol/service.proto */
  rpc intri-stormcontrol-SetEnabled {
    input  {
      uses intri-common:Enabled;
    }
  }
  /* core/stormcontrol/service.proto */
  rpc intri-stormcontrol-GetEnabled {
    output  {
      uses intri-common:Enabled;
    }
  }
  /* core/stormcontrol/service.proto */
  rpc intri-stormcontrol-GetPortConfig {
    output  {
      uses PortConfig;
    }
  }
  /* core/stormcontrol/service.proto */
  rpc intri-stormcontrol-UpdatePortConfigEntry {
    input  {
      uses PortConfigEntry;
    }
  }
  /* core/stormcontrol/service.proto */
  rpc intri-stormcontrol-UpdatePortConfig {
    input  {
      uses PortConfig;
    }
  }

}
