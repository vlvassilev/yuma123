module intri-timesync {

  namespace "intri:intri-timesync";
  prefix "intri-timesync";
  organization "
    Intrising Inc.";
  contact "
    intrising@intrising.com.tw";
  revision 2022-06-24 {
    description "Build date.";
  }

  import intri-device {
    prefix intri-device;
  }
  import intri-empty {
    prefix intri-empty;
  }
  typedef SyncEModeTypeOptions {
    type enumeration {
      enum SYNCE_MODE_TYPE_DISABLED {
        description "[Disabled]";
        value 0;
      }
      enum SYNCE_MODE_TYPE_STATIC {
        description "[Static]";
        value 1;
      }
      enum SYNCE_MODE_TYPE_ESMC {
        description "[ESMC]";
        value 2;
      }
    }
  }
  typedef SyncSourceTypeOptions {
    type enumeration {
      enum SYNC_SOURCE_TYPE_GNSS {
        description "[GNSS]";
        value 0;
      }
      enum SYNC_SOURCE_TYPE_SYNCE {
        description "[SyncE]";
        value 1;
      }
      enum SYNC_SOURCE_TYPE_10MHZ_INPUT {
        description "[10MHz Input]";
        value 2;
      }
      enum SYNC_SOURCE_TYPE_1PPS_INPUT {
        description "[1PPS Input]";
        value 3;
      }
      enum SYNC_SOURCE_TYPE_BITS_INPUT {
        description "[BITS Input]";
        value 4;
      }
      enum SYNC_SOURCE_TYPE_PTP {
        description "[PTP]";
        value 5;
      }
    }
  }
  typedef LockStatusTypeOptions {
    type enumeration {
      enum LOCK_STATUS_TYPE_FREERUN {
        description "[FreeRun]";
        value 0;
      }
      enum LOCK_STATUS_TYPE_LOCK_ACQUISITION {
        description "[Lock Acquisition]";
        value 1;
      }
      enum LOCK_STATUS_TYPE_LOCKED {
        description "[Locked]";
        value 2;
      }
      enum LOCK_STATUS_TYPE_HOLDOVER {
        description "[Holdover]";
        value 3;
      }
    }
  }
  typedef SignalTypeOptions {
    type enumeration {
      enum SIGNAL_TYPE_OK {
        description "[OK]";
        value 0;
      }
      enum SIGNAL_TYPE_LOSS {
        description "[Loss]";
        value 1;
      }
    }
  }
  typedef ToDMessageTypeOptions {
    type enumeration {
      enum TOD_MESSAGE_TYPE_NMEA_GPZDA {
        description "[NMEA GPZDA]";
        value 0;
      }
    }
  }
  typedef GNSSStateTypeOptions {
    type enumeration {
      enum GNSS_STATE_TYPE_DISABLE {
        description "[Disable]";
        value 0;
      }
      enum GNSS_STATE_TYPE_SYNC {
        description "[Sync]";
        value 1;
      }
      enum GNSS_STATE_TYPE_TRACKING {
        description "[Tracking]";
        value 2;
      }
    }
  }
  grouping Config {
    container GNSS {
      uses GNSSConfig;
    }
    container SyncE {
      uses SyncEConfig;
    }
    container SyncSource {
      uses SyncSourceConfig;
    }
    container Reference {
      uses ReferenceOutput;
    }
  }
  grouping GNSSConfig {
    leaf Enabled {
      mandatory "true";
      type boolean;
    }
  }
  grouping SyncEConfig {
    leaf Mode {
      mandatory "true";
      type SyncEModeTypeOptions;
    }
    container ReferenceIdentifyNo {
      uses intri-device:InterfaceIdentify;
    }
  }
  grouping SyncSourceConfig {
    leaf Source {
      mandatory "true";
      type SyncSourceTypeOptions;
    }
  }
  grouping ReferenceOutput {
    container Tod {
      uses ToDConfig;
    }
  }
  grouping ToDConfig {
    leaf Enabled {
      mandatory "true";
      type boolean;
    }
    leaf MessageType {
      mandatory "true";
      type ToDMessageTypeOptions;
    }
  }
  grouping GNSStatus {
    leaf State {
      mandatory "true";
      type GNSSStateTypeOptions;
    }
    leaf Longitude {
      mandatory "true";
      type string;
    }
    leaf Latitude {
      mandatory "true";
      type string;
    }
    leaf DateTime {
      mandatory "true";
      type string;
    }
  }
  grouping SyncEStatus {
    container ReferenceIdentifyNo {
      uses intri-device:InterfaceIdentify;
    }
    leaf Signal {
      mandatory "true";
      type SignalTypeOptions;
    }
    leaf LockStatus {
      mandatory "true";
      type LockStatusTypeOptions;
    }
  }
  grouping SyncSourceStatus {
    leaf LockStatus {
      mandatory "true";
      type LockStatusTypeOptions;
    }
    container List {
      list List_Entry {
        uses SyncSourceInputStatusEntry;
      }
    }
  }
  grouping SyncSourceInputStatusEntry {
    leaf Source {
      mandatory "true";
      type SyncSourceTypeOptions;
    }
    leaf Signal {
      mandatory "true";
      type SignalTypeOptions;
    }
  }
  rpc intri-timesync-TimeSync-SetGNSSConfig {
    input {
      uses GNSSConfig;
    }
  }
  rpc intri-timesync-TimeSync-GetGNSSConfig {
    output {
      uses GNSSConfig;
    }
  }
  rpc intri-timesync-TimeSync-GetGNSSStatus {
    output {
      uses GNSStatus;
    }
  }
  rpc intri-timesync-TimeSync-SetSyncEConfig {
    input {
      uses SyncEConfig;
    }
  }
  rpc intri-timesync-TimeSync-GetSyncEConfig {
    output {
      uses SyncEConfig;
    }
  }
  rpc intri-timesync-TimeSync-GetSyncEStatus {
    output {
      uses SyncEStatus;
    }
  }
  rpc intri-timesync-TimeSync-SetSyncSourceConfig {
    input {
      uses SyncSourceConfig;
    }
  }
  rpc intri-timesync-TimeSync-GetSyncSourceConfig {
    output {
      uses SyncSourceConfig;
    }
  }
  rpc intri-timesync-TimeSync-GetSyncSourceStatus {
    output {
      uses SyncSourceStatus;
    }
  }
  rpc intri-timesync-TimeSync-SetReferenceOutput {
    input {
      uses ReferenceOutput;
    }
  }
  rpc intri-timesync-TimeSync-GetReferenceOutput {
    output {
      uses ReferenceOutput;
    }
  }
}
