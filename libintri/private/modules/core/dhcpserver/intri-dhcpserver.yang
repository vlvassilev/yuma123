module intri-dhcpserver {
  namespace "intri:intri-dhcpserver";
  prefix "intri-dhcpserver";
  import dhcpserverpb {
    prefix "dhcpserverpb";
  }
  organization "Intrising Inc.";
  contact "xxx@intrising.com.tw";
  revision 2022-06-14 {
    description "Build date.";
  }
}
