// Code generated by protoc-gen-yang. DO NOT EDIT.


/* ****************************************************************************************************
 * Import Path : "github.com/Intrising/intri-type/core/network"                                       *
 * Dir Path    : github.com/Intrising/intri-type/core/network                                         *
 * Go Package  : network                                                                              *
 * Files       : 2                                                                                    *
 **************************************************************************************************** */
module intri-network {

  namespace "intri:intri-network";

  prefix "intri-network";

  organization "Intrising Inc.";

  contact "intrising@intrising.com.tw";

  revision 2022-06-23 {
    description "Build date.";
  }

  import intri-common {
    prefix intri-common;
  }
  import intri-empty {
    prefix intri-empty;
  }


  /* **************************************************************************************************
   * Enums       : 2                                                                                  *
   ************************************************************************************************** */
  /* core/network/network.proto */
  typedef IPv4DhcpModeTypeOptions {
    type enumeration {
      enum IPV4_DHCP_MODE_TYPE_DISABLED {
        description "[Static]";
        value 0;
      }
      enum IPV4_DHCP_MODE_TYPE_USE_DHCP {
        description "[Use DHCP]";
        value 1;
      }
      enum IPV4_DHCP_MODE_TYPE_DHCP_WITH_OPTION_66_67 {
        description "[Use DHCP with Option 66/67]";
        value 2;
      }
    }
  }
  /* core/network/network.proto */
  typedef IPV4ConfigDefaultAddressSelectionTypeOptions {
    type enumeration {
      enum IPV4_CONFIG_DEFAULT_ADDRESS_SELECTION_TYPE_PRIMARY {
        description "[Primary]";
        value 0;
      }
      enum IPV4_CONFIG_DEFAULT_ADDRESS_SELECTION_TYPE_SECONDARY {
        description "[Secondary]";
        value 1;
      }
    }
  }


  /* **************************************************************************************************
   * Msgs        : 10                                                                                 *
   ************************************************************************************************** */
  /* core/network/network.proto */
  grouping Config {
    container Basic {
      uses BasicConfig;
    }
    container IP {
      uses IPConfig;
    }
  }
  /* core/network/network.proto */
  grouping BasicConfig {
    leaf HostName {
      type string;
    }
    leaf DomainName {
      type string;
    }
    leaf LocalMTU {
      type int32;
    }
  }
  /* core/network/network.proto */
  grouping IPConfig {
    container V4 {
      uses IPv4Config;
    }
    container V6 {
      uses IPv6Config;
    }
  }
  /* core/network/network.proto */
  grouping IPv4Config {
    leaf DHCPMode {
      type IPv4DhcpModeTypeOptions;
    }
    container Static {
      uses IPv4Static;
    }
  }
  /* core/network/network.proto */
  grouping IPv4Static {
    leaf IPAddress {
      type string;
    }
    leaf SubnetMask {
      type string;
    }
    leaf Gateway {
      type string;
    }
    leaf DNSServer {
      type string;
    }
    leaf SecondaryDeviceIP {
      type string;
    }
    leaf SecondarySubnetMask {
      type string;
    }
    leaf DefaultAddressSelection {
      type IPV4ConfigDefaultAddressSelectionTypeOptions;
    }
  }
  /* core/network/network.proto */
  grouping IPv6Config {
    leaf Enabled {
      type boolean;
    }
    leaf IcmpAutoAddressEnabled {
      type boolean;
    }
    leaf AutoConfigurationEnabled {
      type boolean;
    }
    container Static {
      uses IPv6Static;
    }
  }
  /* core/network/network.proto */
  grouping IPv6Static {
    leaf DNSServer {
      type string;
    }
    leaf IPAddress {
      type string;
    }
  }
  /* core/network/network.proto */
  grouping IPv4Status {
    leaf DynamicDeviceIP {
      type string;
    }
    leaf DynamicSubnetMask {
      type string;
    }
    leaf DynamicGateway {
      type string;
    }
    leaf DynamicDNSServer1 {
      type string;
    }
    leaf DynamicDNSServer2 {
      type string;
    }
    leaf DynamicDNSServer3 {
      type string;
    }
    leaf DynamicDNSServer4 {
      type string;
    }
    leaf OutgoingDeviceIP {
      type string;
    }
  }
  /* core/network/network.proto */
  grouping IPv6StatusEntry {
    leaf IPAddress {
      type string;
    }
    leaf Scope {
      type intri-common:IPv6ScopeTypeOptions;
    }
  }
  /* core/network/network.proto */
  grouping IPv6Status {
    container List {
      list List_Entry {
        uses IPv6StatusEntry;
      }
    }
  }


  /* **************************************************************************************************
   * Services    : 1                                                                                  *
   ************************************************************************************************** */

  /* **************************************************************************************************
   * Service     : Network                                                                            *
   * Methods     : 12                                                                                 *
   ************************************************************************************************** */
  /* core/network/service.proto */
  rpc intri-network-GetConfig {
    output  {
      uses Config;
    }
  }
  /* core/network/service.proto */
  rpc intri-network-GetBasicConfig {
    output  {
      uses BasicConfig;
    }
  }
  /* core/network/service.proto */
  rpc intri-network-SetBasicConfig {
    input  {
      uses BasicConfig;
    }
  }
  /* core/network/service.proto */
  rpc intri-network-GetIPConfig {
    output  {
      uses IPConfig;
    }
  }
  /* core/network/service.proto */
  rpc intri-network-GetIPv4Config {
    output  {
      uses IPv4Config;
    }
  }
  /* core/network/service.proto */
  rpc intri-network-SetIPv4Config {
    input  {
      uses IPv4Config;
    }
  }
  /* core/network/service.proto */
  rpc intri-network-GetIPv6Config {
    output  {
      uses IPv6Config;
    }
  }
  /* core/network/service.proto */
  rpc intri-network-SetIPv6Config {
    input  {
      uses IPv6Config;
    }
  }
  /* core/network/service.proto */
  rpc intri-network-GetV4Status {
    output  {
      uses IPv4Status;
    }
  }
  /* core/network/service.proto */
  rpc intri-network-GetV6Status {
    output  {
      uses IPv6Status;
    }
  }
  /* core/network/service.proto */
  rpc intri-network-GetIPv6Address {
    output  {
      uses intri-common:IPv6List;
    }
  }
  /* core/network/service.proto */
  rpc intri-network-GetIPv4Address {
    output  {
      uses intri-common:IPAddress;
    }
  }

}
