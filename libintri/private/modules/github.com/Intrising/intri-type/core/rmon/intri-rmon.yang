// Code generated by protoc-gen-yang. DO NOT EDIT.


/* ****************************************************************************************************
 * Import Path : "github.com/Intrising/intri-type/core/rmon"                                          *
 * Dir Path    : github.com/Intrising/intri-type/core/rmon                                            *
 * Go Package  : rmon                                                                                 *
 * Files       : 2                                                                                    *
 **************************************************************************************************** */
module intri-rmon {

  namespace "intri:intri-rmon";

  prefix "intri-rmon";

  organization "Intrising Inc.";

  contact "intrising@intrising.com.tw";

  revision 2022-06-23 {
    description "Build date.";
  }

  import intri-device {
    prefix intri-device;
  }
  import intri-empty {
    prefix intri-empty;
  }


  /* **************************************************************************************************
   * Enums       : 1                                                                                  *
   ************************************************************************************************** */
  /* core/rmon/rmon.proto */
  typedef UtilizationIntervalTypeOptions {
    type enumeration {
      enum UTILIZATION_INTERVAL_TYPE_NOW {
        description "[Now]";
        value 0;
      }
      enum UTILIZATION_INTERVAL_TYPE_30_SECONDS {
        description "[30s]";
        value 1;
      }
      enum UTILIZATION_INTERVAL_TYPE_5_MINUTES {
        description "[5min]";
        value 2;
      }
    }
  }


  /* **************************************************************************************************
   * Msgs        : 9                                                                                  *
   ************************************************************************************************** */
  /* core/rmon/rmon.proto */
  grouping IngressEntry {
    container IdentifyNo {
      uses intri-device:InterfaceIdentify;
    }
    leaf InGoodOctets {
      type uint64;
    }
    leaf InBadOctets {
      type uint64;
    }
    leaf InTotalPackets {
      type uint64;
    }
    leaf InUnicasts {
      type uint64;
    }
    leaf InNonUnicasts {
      type uint64;
    }
    leaf InBroadcasts {
      type uint64;
    }
    leaf InMulticasts {
      type uint64;
    }
    leaf InPause {
      type uint64;
    }
    leaf InTotalReceiveErrors {
      type uint64;
    }
    leaf InUndersize {
      type uint64;
    }
    leaf InOversize {
      type uint64;
    }
    leaf InFragments {
      type uint64;
    }
    leaf InJabber {
      type uint64;
    }
    leaf InFcsErrors {
      type uint64;
    }
    leaf InDiscarded {
      type uint64;
    }
  }
  /* core/rmon/rmon.proto */
  grouping Ingress {
    container List {
      list List_Entry {
        uses IngressEntry;
      }
    }
  }
  /* core/rmon/rmon.proto */
  grouping EgressEntry {
    container IdentifyNo {
      uses intri-device:InterfaceIdentify;
    }
    leaf OutGoodOctets {
      type uint64;
    }
    leaf OutUnicasts {
      type uint64;
    }
    leaf OutNonUnicasts {
      type uint64;
    }
    leaf OutBroadcasts {
      type uint64;
    }
    leaf OutMulticasts {
      type uint64;
    }
    leaf OutPause {
      type uint64;
    }
    leaf OutDeferred {
      type uint64;
    }
    leaf OutTotalCollisions {
      type uint64;
    }
    leaf OutTotalPackets {
      type uint64;
    }
    leaf OutExcessiveCollisions {
      type uint64;
    }
    leaf OutLateCollisions {
      type uint64;
    }
    leaf OutFcsErrors {
      type uint64;
    }
    leaf OutDroppedPackets {
      type uint64;
    }
    leaf OutMultipleCollisions {
      type uint64;
    }
  }
  /* core/rmon/rmon.proto */
  grouping Egress {
    container List {
      list List_Entry {
        uses EgressEntry;
      }
    }
  }
  /* core/rmon/rmon.proto */
  grouping HistogramEntry {
    container IdentifyNo {
      uses intri-device:InterfaceIdentify;
    }
    leaf In_64Octets {
      type uint64;
    }
    leaf In_65To_127Octets {
      type uint64;
    }
    leaf In_128To_255Octets {
      type uint64;
    }
    leaf In_256To_511Octets {
      type uint64;
    }
    leaf In_512To_1023Octets {
      type uint64;
    }
    leaf In_1024ToMaxOctets {
      type uint64;
    }
  }
  /* core/rmon/rmon.proto */
  grouping Histogram {
    container List {
      list List_Entry {
        uses HistogramEntry;
      }
    }
  }
  /* core/rmon/rmon.proto */
  grouping UtilizationRate {
    leaf Type {
      type UtilizationIntervalTypeOptions;
    }
    leaf Rate {
      type int32;
    }
  }
  /* core/rmon/rmon.proto */
  grouping UtilizationEntry {
    container IdentifyNo {
      uses intri-device:InterfaceIdentify;
    }
    container Ingress {
      list Ingress_Entry {
        uses UtilizationRate;
      }
    }
    container Egress {
      list Egress_Entry {
        uses UtilizationRate;
      }
    }
  }
  /* core/rmon/rmon.proto */
  grouping Utilization {
    container List {
      list List_Entry {
        uses UtilizationEntry;
      }
    }
  }


  /* **************************************************************************************************
   * Services    : 1                                                                                  *
   ************************************************************************************************** */

  /* **************************************************************************************************
   * Service     : RMON                                                                               *
   * Methods     : 5                                                                                  *
   ************************************************************************************************** */
  /* core/rmon/service.proto */
  rpc intri-rmon-RunClearAllCounter {
  }
  /* core/rmon/service.proto */
  rpc intri-rmon-GetIngress {
    input  {
      uses intri-device:PortList;
    }
    output  {
      uses Ingress;
    }
  }
  /* core/rmon/service.proto */
  rpc intri-rmon-GetEgress {
    input  {
      uses intri-device:PortList;
    }
    output  {
      uses Egress;
    }
  }
  /* core/rmon/service.proto */
  rpc intri-rmon-GetHistogram {
    input  {
      uses intri-device:PortList;
    }
    output  {
      uses Histogram;
    }
  }
  /* core/rmon/service.proto */
  rpc intri-rmon-GetUtilization {
    input  {
      uses intri-device:PortList;
    }
    output  {
      uses Utilization;
    }
  }

}
