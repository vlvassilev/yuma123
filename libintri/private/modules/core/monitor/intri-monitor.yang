module intri-monitor {
  namespace "intri:intri-monitor";
  prefix "intri-monitor";
  import monitorpb {
    prefix "monitorpb";
  }
  organization "Intrising Inc.";
  contact "xxx@intrising.com.tw";
  revision 2022-06-14 {
    description "Build date.";
  }
}
