module intri-maintenance {
  namespace "intri:intri-maintenance";
  prefix "intri-maintenance";
  organization "Intrising Inc.";
  contact "xxx@intrising.com.tw";
  revision 2022-06-14 {
    description "Build date.";
  }
}
