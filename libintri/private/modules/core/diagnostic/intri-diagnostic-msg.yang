submodule intri-diagnostic-msg {
  belongs-to "intri-diagnostic" {
    prefix "intri-diagnostic-msg";
  }
  include intri-diagnostic-enum;
  import diagnosticpb {
    prefix "diagnosticpb";
  }
  revision 2022-06-14 {
    description "Build date.";
  }
  // core/diagnostic/diagnostic.proto
  grouping ARPEntry {
    leaf ARPEntry_IPAddr {
      type string;
    }
    leaf ARPEntry_MACAddr {
      type string;
    }
  }
  // core/diagnostic/diagnostic.proto
  grouping ARPTables {
    container ARPTables_List {
      uses diagnosticpb:ARPEntry;
    }
  }
}
