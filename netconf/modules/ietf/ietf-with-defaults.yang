module ietf-with-defaults {
    namespace "urn:ietf:params:netconf:capability:with-defaults:1.0";

    prefix nwd;

    // for the uri data type
    // import ietf-netconf { prefix nc; }
    import yuma-netconf { prefix nc; }

    description
     "This module defines a capability-based extension to the
      NETCONF protocol that allows the NETCONF client to control
      whether default values are part of NETCONF
      <rpc-reply> messages.

      Copyright (c) 2009 IETF Trust and the persons identified as
      the document authors.  All rights reserved.

      Redistribution and use in source and binary forms, with or
      without modification, are permitted provided that the
      following conditions are met:

      - Redistributions of source code must retain the above
        copyright notice, this list of conditions and the
        following disclaimer.

      - Redistributions in binary form must reproduce the above
        copyright notice, this list of conditions and the
        following disclaimer in the documentation and/or other
        materials provided with the distribution.

      - Neither the name of Internet Society, IETF or IETF
        Trust, nor the names of specific contributors, may be
        used to endorse or promote products derived from this
        software without specific prior written permission.

      THIS SOFTWARE IS PROVIDED BY THE COPYRIGHT HOLDERS AND
      CONTRIBUTORS 'AS IS' AND ANY EXPRESS OR IMPLIED
      WARRANTIES, INCLUDING, BUT NOT LIMITED TO, THE IMPLIED
      WARRANTIES OF MERCHANTABILITY AND FITNESS FOR A PARTICULAR
      PURPOSE ARE DISCLAIMED.  IN NO EVENT SHALL THE COPYRIGHT
      OWNER OR CONTRIBUTORS BE LIABLE FOR ANY DIRECT, INDIRECT,
      INCIDENTAL, SPECIAL, EXEMPLARY, OR CONSEQUENTIAL DAMAGES
      (INCLUDING, BUT NOT LIMITED TO, PROCUREMENT OF SUBSTITUTE
      GOODS OR SERVICES; LOSS OF USE, DATA, OR PROFITS; OR
      BUSINESS INTERRUPTION) HOWEVER CAUSED AND ON ANY THEORY OF
      LIABILITY, WHETHER IN CONTRACT, STRICT LIABILITY, OR TORT
      (INCLUDING NEGLIGENCE OR OTHERWISE) ARISING IN ANY WAY OUT
      OF THE USE OF THIS SOFTWARE, EVEN IF ADVISED OF THE
      POSSIBILITY OF SUCH DAMAGE.

      This version of this YANG module is part of RFC XXXX; see
      the RFC itself for full legal notices.";

    // RFC Ed.: replace XXXX with actual RFC number and remove this note

    reference "RFC XXXX";

    // RFC Ed.: replace XXXX with actual RFC number and remove this note

    // reference "draft-ietf-netconf-with-defaults-03.txt";

    // RFC Ed.: remove the reference statement above and this note.

    contact
      "Send comments to the NETCONF WG mailing list.
       <netconf@ietf.org>";

    revision 2009-07-01 {
      description
        "Initial version";
    }

    // with-defaults capability defined as a feature
    feature with-defaults {
        description
          "NETCONF :with-defaults capability;
           If the agent advertises the :with-defaults
           capability for a session, then this feature MUST
           also be enabled for that session.  Otherwise,
           this feature MUST NOT be enabled.";
        // RFC Ed.: replace XXXX with actual RFC number and
        // remove this note
        reference "RFC XXXX";
    }

    typedef with-defaults-mode-type {
       description
         "Possible modes to report default data in
          rpc-reply messages.";
       type enumeration {
          enum report-all {
              description
                "All default data is always reported.";
          }
          enum trim {
              description
                "Values are not reported if they match the default.";
          }
          enum explicit {
              description
                "Report values if they are explicitly set.
                 For state data this has the same effect
                 as report-all";
          }
      }
    }

    // extending the get-config operation
    augment /nc:get-config/nc:input {
        leaf with-defaults {
            type with-defaults-mode-type;
        }
    }

    // extending the get operation
    augment /nc:get/nc:input {
        leaf with-defaults {
            type with-defaults-mode-type;
        }
    }

    // extending the copy-congig operation
    augment /nc:copy-config/nc:input {
        leaf with-defaults {
            type with-defaults-mode-type;
        }
    }
}
