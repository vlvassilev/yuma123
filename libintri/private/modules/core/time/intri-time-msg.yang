submodule intri-time-msg {
  belongs-to "intri-time" {
    prefix "intri-time-msg";
  }
  include intri-time-enum;
  import timepb {
    prefix "timepb";
  }
  import protobufpb {
    prefix "protobufpb";
  }
  revision 2022-06-14 {
    description "Build date.";
  }
  // core/time/time.proto
  grouping Config {
    leaf Config_Mode {
      type timepb:ModeTypeOptions;
    }
    leaf Config_MainNTPServer {
      type string;
    }
    leaf Config_BackupNTPServer {
      type string;
    }
    leaf Config_TrustedServerEnabled {
      type boolean;
    }
    leaf Config_SyncInterval {
      type int32;
    }
    leaf Config_TimeZone {
      type string;
    }
    leaf Config_TimeFormat {
      type string;
    }
    leaf Config_DateFormat {
      type string;
    }
    leaf Config_Manual {
      type string;
    }
  }
  // core/time/time.proto
  grouping ListTimeZones {
    leaf ListTimeZones_List {
      type string;
    }
  }
  // core/time/time.proto
  grouping Status {
    leaf Status_Status {
      type timepb:StatusTypeOptions;
    }
    leaf Status_LocalTime {
      type string;
    }
    leaf Status_LocalDate {
      type string;
    }
    leaf Status_UsedNTPServer {
      type string;
    }
  }
  // core/time/time.proto
  grouping RequestWithTimestamp {
    container RequestWithTimestamp_Ts {
      uses protobufpb:Timestamp;
    }
  }
  // core/time/time.proto
  grouping RequestWithInt64 {
    leaf RequestWithInt64_Ts {
      type int64;
    }
  }
  // core/time/time.proto
  grouping Response {
    leaf Response_Ts {
      type string;
    }
  }
}
