// Code generated by protoc-gen-yang. DO NOT EDIT.


/* ****************************************************************************************************
 * Import Path : "github.com/Intrising/intri-type/core/fdb"                                           *
 * Dir Path    : github.com/Intrising/intri-type/core/fdb                                             *
 * Go Package  : fdb                                                                                  *
 * Files       : 3                                                                                    *
 **************************************************************************************************** */
module intri-fdb {

  namespace "intri:intri-fdb";

  prefix "intri-fdb";

  organization "Intrising Inc.";

  contact "intrising@intrising.com.tw";

  revision 2022-06-23 {
    description "Build date.";
  }

  import intri-device {
    prefix intri-device;
  }
  import intri-empty {
    prefix intri-empty;
  }
  import intri-event {
    prefix intri-event;
  }


  /* **************************************************************************************************
   * Enums       : 2                                                                                  *
   ************************************************************************************************** */
  /* core/fdb/common.proto */
  typedef MACTableStateTypeOptions {
    type enumeration {
      enum MAC_TABLE_STATE_TYPE_UNUSED {
        description "[Unused] The field was not set";
        value 0;
      }
      enum MAC_TABLE_STATE_TYPE_OTHER {
        description "[Other] Unspecified entry state";
        value 1;
      }
      enum MAC_TABLE_STATE_TYPE_INVALID {
        description "[Invalid] This entry is not longer valid (aged)";
        value 2;
      }
      enum MAC_TABLE_STATE_TYPE_LEARNED {
        description "[Learned] This entry was learned and is valid";
        value 3;
      }
      enum MAC_TABLE_STATE_TYPE_SELF {
        description "[Self] This entry corresponds to the local MAC address";
        value 4;
      }
      enum MAC_TABLE_STATE_TYPE_PACC {
        description "[PACC] This entry was created by port access control";
        value 5;
      }
      enum MAC_TABLE_STATE_TYPE_MULTICAST {
        description "* This is an internal multicast address";
        value 6;
      }
      enum MAC_TABLE_STATE_TYPE_REJECT {
        description "[Reject] This entry was rejected because of dropping";
        value 7;
      }
    }
  }
  /* core/fdb/common.proto */
  typedef PortOccupiedTypeOptions {
    type enumeration {
      enum PORT_OCCUPIED_TYPE_NONE {
        description "[None]";
        value 0;
      }
      enum PORT_OCCUPIED_TYPE_PACC {
        description "[PACC]";
        value 1;
      }
      enum PORT_OCCUPIED_TYPE_PORT_SECURITY {
        description "[Port Security]";
        value 2;
      }
    }
  }


  /* **************************************************************************************************
   * Msgs        : 14                                                                                 *
   ************************************************************************************************** */
  /* core/fdb/fdb.proto */
  grouping Config {
    container AgeTime {
      uses AgingTime;
    }
    container PortLimit {
      uses PortLearningLimit;
    }
    container ForwardConfig {
      uses ForwardConfig;
    }
    container DropConfig {
      uses DropConfig;
    }
  }
  /* core/fdb/fdb.proto */
  grouping AgingTime {
    leaf GlobalAgingTime {
      type int32;
    }
  }
  /* core/fdb/fdb.proto */
  grouping ForwardConfig {
    container List {
      list List_Entry {
        uses ForwardConfigEntry;
      }
    }
  }
  /* core/fdb/fdb.proto */
  grouping ForwardConfigEntry {
    leaf MACAddress {
      type string;
    }
    leaf VlanID {
      type int32;
    }
    container IdentifyNo {
      uses intri-device:InterfaceIdentify;
    }
  }
  /* core/fdb/fdb.proto */
  grouping DropConfig {
    container List {
      list List_Entry {
        uses DropConfigEntry;
      }
    }
  }
  /* core/fdb/fdb.proto */
  grouping DropConfigEntry {
    leaf MACAddress {
      type string;
    }
    leaf VlanID {
      type int32;
    }
    container IdentifyNo {
      uses intri-device:InterfaceIdentify;
    }
  }
  /* core/fdb/fdb.proto */
  grouping PortLearningLimit {
    container List {
      list List_Entry {
        uses PortLearningLimitEntry;
      }
    }
  }
  /* core/fdb/fdb.proto */
  grouping PortLearningLimitEntry {
    container IdentifyNo {
      uses intri-device:InterfaceIdentify;
    }
    leaf Limit {
      type int32;
    }
  }
  /* core/fdb/fdb.proto */
  grouping Info {
    leaf UsedAgingTime {
      type int32;
    }
    leaf NumberOfFreeEntries {
      type int32;
    }
    leaf NumberOfUsedEntries {
      type int32;
    }
    leaf NumberOfMacUnicastDynamicEntries {
      type int32;
    }
    leaf NumberOfMacUnicastStaticEntries {
      type int32;
    }
    leaf NumberOfMacMulticastDynamicEntries {
      type int32;
    }
    leaf NumberOfMacMulticastStaticEntries {
      type int32;
    }
    leaf NumberOfIpv4MulticastEntries {
      type int32;
    }
    leaf NumberOfIpv6MulticastEntries {
      type int32;
    }
  }
  /* core/fdb/fdb.proto */
  grouping Status {
    container List {
      list List_Entry {
        uses StatusEntry;
      }
    }
  }
  /* core/fdb/fdb.proto */
  grouping StatusEntry {
    leaf VlanID {
      type int32;
    }
    leaf MACAddress {
      type string;
    }
    container IdentifyNo {
      uses intri-device:InterfaceIdentify;
    }
    leaf State {
      type MACTableStateTypeOptions;
    }
  }
  /* core/fdb/fdb.proto */
  grouping SpecificMac {
    leaf MACAddress {
      type string;
    }
  }
  /* core/fdb/fdb.proto */
  grouping FlushOption {
    leaf DynamicAll {
      type boolean;
    }
    container Identify {
      uses intri-device:PortList;
    }
  }
  /* core/fdb/fdb.proto */
  grouping PortOccupied {
    container IdentifyNo {
      uses intri-device:InterfaceIdentify;
    }
    leaf Type {
      type PortOccupiedTypeOptions;
    }
  }


  /* **************************************************************************************************
   * Services    : 1                                                                                  *
   ************************************************************************************************** */

  /* **************************************************************************************************
   * Service     : FDB                                                                                *
   * Methods     : 26                                                                                 *
   ************************************************************************************************** */
  /* core/fdb/service.proto */
  rpc intri-fdb-GetConfig {
    output  {
      uses Config;
    }
  }
  /* core/fdb/service.proto */
  rpc intri-fdb-GetMACAgingTime {
    output  {
      uses AgingTime;
    }
  }
  /* core/fdb/service.proto */
  rpc intri-fdb-SetMACAgingTime {
    input  {
      uses AgingTime;
    }
  }
  /* core/fdb/service.proto */
  rpc intri-fdb-GetFDBForwardTable {
    output  {
      uses ForwardConfig;
    }
  }
  /* core/fdb/service.proto */
  rpc intri-fdb-AddForwardMACAddress {
    input  {
      uses ForwardConfig;
    }
  }
  /* core/fdb/service.proto */
  rpc intri-fdb-DeleteForwardMACAddress {
    input  {
      uses ForwardConfig;
    }
  }
  /* core/fdb/service.proto */
  rpc intri-fdb-UpdateForwardMACAddress {
    input  {
      uses ForwardConfig;
    }
  }
  /* core/fdb/service.proto */
  rpc intri-fdb-GetFDBDropTable {
    output  {
      uses DropConfig;
    }
  }
  /* core/fdb/service.proto */
  rpc intri-fdb-AddDropMACAddress {
    input  {
      uses DropConfig;
    }
  }
  /* core/fdb/service.proto */
  rpc intri-fdb-DeleteDropMACAddress {
    input  {
      uses DropConfig;
    }
  }
  /* core/fdb/service.proto */
  rpc intri-fdb-UpdateDropMACAddress {
    input  {
      uses DropConfig;
    }
  }
  /* core/fdb/service.proto */
  rpc intri-fdb-UpdatePortLearningLimit {
    input  {
      uses PortLearningLimit;
    }
  }
  /* core/fdb/service.proto */
  rpc intri-fdb-GetInfo {
    output  {
      uses Info;
    }
  }
  /* core/fdb/service.proto */
  rpc intri-fdb-GetTable {
    output  {
      uses Status;
    }
  }
  /* core/fdb/service.proto */
  rpc intri-fdb-GetAuthorizedTable {
    output  {
      uses Status;
    }
  }
  /* core/fdb/service.proto */
  rpc intri-fdb-GetSecurityTable {
    output  {
      uses Status;
    }
  }
  /* core/fdb/service.proto */
  rpc intri-fdb-GetSpecificTable {
    input  {
      uses SpecificMac;
    }
    output  {
      uses Status;
    }
  }
  /* core/fdb/service.proto */
  rpc intri-fdb-RunClearMACTable {
  }
  /* core/fdb/service.proto */
  rpc intri-fdb-RunClearMACTableForInterface {
    input  {
      uses FlushOption;
    }
  }
  /* core/fdb/service.proto */
  rpc intri-fdb-AddEntry {
    input  {
      uses intri-event:FDBEntry;
    }
  }
  /* core/fdb/service.proto */
  rpc intri-fdb-DeleteEntry {
    input  {
      uses intri-event:FDBEntry;
    }
  }
  /* core/fdb/service.proto */
  rpc intri-fdb-UpdateEntry {
    input  {
      uses intri-event:FDBEntry;
    }
  }
  /* core/fdb/service.proto */
  rpc intri-fdb-UpdatePortOccupied {
    input  {
      uses PortOccupied;
    }
  }
  /* core/fdb/service.proto */
  rpc intri-fdb-AddMulticastEntry {
    input  {
      uses intri-event:FDBEntry;
    }
  }
  /* core/fdb/service.proto */
  rpc intri-fdb-DeleteMulticastEntry {
    input  {
      uses intri-event:FDBEntry;
    }
  }
  /* core/fdb/service.proto */
  rpc intri-fdb-UpdateMulticastEntry {
    input  {
      uses intri-event:FDBEntry;
    }
  }

}
