// Code generated by protoc-gen-yang. DO NOT EDIT.


/* ****************************************************************************************************
 * Import Path : "github.com/Intrising/intri-type/core/acl"                                           *
 * Dir Path    : github.com/Intrising/intri-type/core/acl                                             *
 * Go Package  : acl                                                                                  *
 * Files       : 3                                                                                    *
 **************************************************************************************************** */
module intri-acl {

  namespace "intri:intri-acl";

  prefix "intri-acl";

  organization "Intrising Inc.";

  contact "intrising@intrising.com.tw";

  revision 2022-06-23 {
    description "Build date.";
  }

  import intri-device {
    prefix intri-device;
  }
  import intri-empty {
    prefix intri-empty;
  }
  import intri-common {
    prefix intri-common;
  }


  /* **************************************************************************************************
   * Enums       : 3                                                                                  *
   ************************************************************************************************** */
  /* core/acl/common.proto */
  typedef RuleActionTypeOptions {
    type enumeration {
      enum RULE_ACTION_TYPE_UNUSED {
        description "[Unused] this rule is unused yet";
        value 0;
      }
      enum RULE_ACTION_TYPE_PERMIT {
        description "[Permit] this rule action will permit packet";
        value 1;
      }
      enum RULE_ACTION_TYPE_DENY {
        description "[Deny] this rule action will deny packet";
        value 2;
      }
      enum RULE_ACTION_TYPE_MIRROR {
        description "*internal usage";
        value 3;
      }
    }
  }
  /* core/acl/common.proto */
  typedef RuleParamTypeOptions {
    type enumeration {
      enum RULE_PARAM_TYPE_MAC {
        description "[MAC] this rule param is MAC address specification";
        value 0;
      }
      enum RULE_PARAM_TYPE_IP_V_4 {
        description "[IPv4] this rule param is IPv4 address specification";
        value 1;
      }
      enum RULE_PARAM_TYPE_IP_V_6 {
        description "[IPv6] this rule param is IPv6 address specification";
        value 2;
      }
    }
  }
  /* core/acl/common.proto */
  typedef RuleDirectionTypeOptions {
    type enumeration {
      enum RULE_DIRECTION_TYPE_INGRESS {
        description "*internal usage";
        value 0;
      }
      enum RULE_DIRECTION_TYPE_EGRESS {
        description "*internal usage";
        value 1;
      }
    }
  }


  /* **************************************************************************************************
   * Msgs        : 24                                                                                 *
   ************************************************************************************************** */
  /* core/acl/acl.proto */
  grouping Config {
    container Interfaces {
      uses InterfaceList;
    }
    container AclList {
      uses ACLList;
    }
    container AceList {
      uses ACEList;
    }
    container Binding {
      uses BindingList;
    }
    container Flow {
      uses FlowMirroringList;
    }
  }
  /* core/acl/acl.proto */
  grouping InterfaceList {
    container List {
      list List_Entry {
        uses InterfaceEntry;
      }
    }
  }
  /* core/acl/acl.proto */
  grouping InterfaceEntry {
    container IdentifyNo {
      uses intri-device:InterfaceIdentify;
    }
    leaf IngressAclName {
      type string;
    }
    leaf EgressAclName {
      type string;
    }
  }
  /* core/acl/acl.proto */
  grouping ACLList {
    container List {
      list List_Entry {
        uses ACLEntry;
      }
    }
  }
  /* core/acl/acl.proto */
  grouping ACLEntry {
    leaf Name {
      type string;
    }
    container RuleList {
      leaf-list RuleList_Entry {
        type string;
      }
    }
  }
  /* core/acl/acl.proto */
  grouping ACEList {
    container List {
      list List_Entry {
        uses ACEEntry;
      }
    }
  }
  /* core/acl/acl.proto */
  grouping ACEEntry {
    leaf Name {
      type string;
    }
    leaf Action {
      type RuleActionTypeOptions;
    }
    leaf Priority {
      type int32;
    }
    leaf TimeRangeName {
      type string;
    }
    leaf ParamType {
      type RuleParamTypeOptions;
    }
    choice Param {
      container Mac {
        uses RuleMAC;
      }
      container IPv4 {
        uses RuleIPv4;
      }
      container IPv6 {
        uses RuleIPv6;
      }
      container MacIPv4 {
        uses RuleMACIPv4;
      }
      container MacIPv6 {
        uses RuleMACIPv6;
      }
    }
  }
  /* core/acl/acl.proto */
  grouping RuleVlan {
    leaf VlanID {
      type int32;
    }
    leaf VlanIDMask {
      type int32;
    }
  }
  /* core/acl/acl.proto */
  grouping RuleMACIPv4 {
    container Mac {
      uses RuleMAC;
    }
    container IPv4 {
      uses RuleIPv4;
    }
  }
  /* core/acl/acl.proto */
  grouping RuleMACIPv6 {
    container Mac {
      uses RuleMAC;
    }
    container IPv6 {
      uses RuleIPv6;
    }
  }
  /* core/acl/acl.proto */
  grouping RuleMAC {
    container EtherType {
      uses EtherTypeConfig;
    }
    container Source {
      uses MACConfig;
    }
    container Destination {
      uses MACConfig;
    }
    leaf VlanId {
      type int32;
    }
  }
  /* core/acl/acl.proto */
  grouping MACConfig {
    leaf Address {
      type string;
    }
    leaf AddressMask {
      type string;
    }
  }
  /* core/acl/acl.proto */
  grouping EtherTypeConfig {
    leaf Type {
      type string;
    }
    leaf EtherTypeMask {
      type string;
    }
  }
  /* core/acl/acl.proto */
  grouping IPProtocolConfig {
    leaf Protocol {
      type string;
    }
    leaf ProtocolMask {
      type string;
    }
  }
  /* core/acl/acl.proto */
  grouping RuleIPv4 {
    container Protocol {
      uses IPProtocolConfig;
    }
    container Source {
      uses IPv4Config;
    }
    container Destination {
      uses IPv4Config;
    }
    container Layer4Port {
      uses RuleLayer4Port;
    }
  }
  /* core/acl/acl.proto */
  grouping IPv4Config {
    leaf Address {
      type string;
    }
    leaf AddressMask {
      type string;
    }
  }
  /* core/acl/acl.proto */
  grouping RuleIPv6 {
    container NextHeader {
      uses IPProtocolConfig;
    }
    container Source {
      uses IPv6Config;
    }
    container Destination {
      uses IPv6Config;
    }
    container Layer4Port {
      uses RuleLayer4Port;
    }
  }
  /* core/acl/acl.proto */
  grouping IPv6Config {
    leaf Address {
      type string;
    }
    leaf AddressMask {
      type string;
    }
  }
  /* core/acl/acl.proto */
  grouping RuleLayer4Port {
    container Source {
      uses IPWithLayer4PortConfig;
    }
    container Destination {
      uses IPWithLayer4PortConfig;
    }
  }
  /* core/acl/acl.proto */
  grouping IPWithLayer4PortConfig {
    leaf PortNumber {
      type int32;
    }
    leaf PortNumberMask {
      type int32;
    }
  }
  /* core/acl/acl.proto */
  grouping BindingList {
    container List {
      list List_Entry {
        uses BindingEntry;
      }
    }
  }
  /* core/acl/acl.proto */
  grouping BindingEntry {
    leaf Name {
      type string;
    }
    container IdentifyNo {
      uses intri-device:InterfaceIdentify;
    }
    leaf Mac {
      type string;
    }
    leaf ParamType {
      type RuleParamTypeOptions;
    }
    choice Param {
      leaf IPv4 {
        type string;
      }
      leaf IPv6 {
        type string;
      }
    }
  }
  /* core/acl/acl.proto */
  grouping FlowMirroringEntry {
    leaf Name {
      type string;
    }
    container ACLNameList {
      leaf-list ACLNameList_Entry {
        type string;
      }
    }
    container SourceList {
      list SourceList_Entry {
        uses intri-device:InterfaceIdentify;
      }
    }
    container Destination {
      uses intri-device:InterfaceIdentify;
    }
  }
  /* core/acl/acl.proto */
  grouping FlowMirroringList {
    container List {
      list List_Entry {
        uses FlowMirroringEntry;
      }
    }
  }


  /* **************************************************************************************************
   * Services    : 1                                                                                  *
   ************************************************************************************************** */

  /* **************************************************************************************************
   * Service     : ACL                                                                                *
   * Methods     : 20                                                                                 *
   ************************************************************************************************** */
  /* core/acl/service.proto */
  rpc intri-acl-GetConfig {
    output  {
      uses Config;
    }
  }
  /* core/acl/service.proto */
  rpc intri-acl-GetInterfaceList {
    output  {
      uses InterfaceList;
    }
  }
  /* core/acl/service.proto */
  rpc intri-acl-UpdateInterface {
    input  {
      uses InterfaceEntry;
    }
  }
  /* core/acl/service.proto */
  rpc intri-acl-UpdateInterfaceList {
    input  {
      uses InterfaceList;
    }
  }
  /* core/acl/service.proto */
  rpc intri-acl-GetACLList {
    output  {
      uses ACLList;
    }
  }
  /* core/acl/service.proto */
  rpc intri-acl-AddACL {
    input  {
      uses ACLEntry;
    }
  }
  /* core/acl/service.proto */
  rpc intri-acl-DeleteACL {
    input  {
      uses intri-common:Name;
    }
  }
  /* core/acl/service.proto */
  rpc intri-acl-UpdateACL {
    input  {
      uses ACLEntry;
    }
  }
  /* core/acl/service.proto */
  rpc intri-acl-GetACEList {
    output  {
      uses ACEList;
    }
  }
  /* core/acl/service.proto */
  rpc intri-acl-AddACE {
    input  {
      uses ACEEntry;
    }
  }
  /* core/acl/service.proto */
  rpc intri-acl-DeleteACE {
    input  {
      uses intri-common:Name;
    }
  }
  /* core/acl/service.proto */
  rpc intri-acl-UpdateACE {
    input  {
      uses ACEEntry;
    }
  }
  /* core/acl/service.proto */
  rpc intri-acl-GetBindingList {
    output  {
      uses BindingList;
    }
  }
  /* core/acl/service.proto */
  rpc intri-acl-AddBinding {
    input  {
      uses BindingEntry;
    }
  }
  /* core/acl/service.proto */
  rpc intri-acl-DeleteBinding {
    input  {
      uses intri-common:Name;
    }
  }
  /* core/acl/service.proto */
  rpc intri-acl-UpdateBinding {
    input  {
      uses BindingEntry;
    }
  }
  /* core/acl/service.proto */
  rpc intri-acl-GetFlowMirroringList {
    output  {
      uses FlowMirroringList;
    }
  }
  /* core/acl/service.proto */
  rpc intri-acl-AddFlowMirroring {
    input  {
      uses FlowMirroringEntry;
    }
  }
  /* core/acl/service.proto */
  rpc intri-acl-DeleteFlowMirroring {
    input  {
      uses intri-common:Name;
    }
  }
  /* core/acl/service.proto */
  rpc intri-acl-UpdateFlowMirroring {
    input  {
      uses FlowMirroringEntry;
    }
  }

}
