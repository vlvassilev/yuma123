module intri-device {

  namespace "http://intri.com.tw";

  prefix intri-device;

  organization 
    "Intrising Inc.";

  contact 
    "xxx <xxx@intrising.com.tw>";

  description 
    "internal APIs";

  revision 2022-05-24 {
    description "Test progress.";
  }

  container api-gets {
    config false;

    description
      "/api-gets call the internal APIs to get information.";

    container test-feat {
      description
        "/api-gets/test-feat call the test API to get dynamic counter.";

      leaf counter {
        type uint64;
        description
          "Test for the counter of the calls get times";
      }
    }

    container test-mac-addr {
      description
        "/api-gets/test-addr call the test API to get device mac address.";

      leaf mac-addr {
        type string;
        description
          "Test get device mac address";
      }
    }
  }
}
