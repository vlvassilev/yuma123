module mod1 {
  yang-version 1.1;

  namespace "http://yuma123.org/ns/test/yangcli/tab-completion-union/mod1";
  prefix m1;

  organization
    "yuma123.org";

  description 'For testing tab completion';

  revision 2020-02-17 {
    description
      "Initial version";
  }

  identity foo;
  identity bar;

  identity first-foo {
    base "foo";
  }
  identity second-foo {
    base "foo";
  }
  identity third-bar {
    base "bar";
  }
  identity fourth-bar {
    base "bar";
  }

  container u1 {
    leaf u2 {
      type union {
        type identityref {
          base "foo";
        }
        type identityref {
          base "bar";
        }
      }
    }
  }
}
