submodule intri-cdp-msg {
  belongs-to "intri-cdp" {
    prefix "intri-cdp-msg";
  }
  include intri-cdp-enum;
  import cdppb {
    prefix "cdppb";
  }
  import devicepb {
    prefix "devicepb";
  }
  revision 2022-06-14 {
    description "Build date.";
  }
  // core/cdp/cdp.proto
  grouping Config {
    container Config_SystemConfig {
      uses cdppb:SystemConfig;
    }
  }
  // core/cdp/cdp.proto
  grouping SystemConfig {
    leaf SystemConfig_Enabled {
      type boolean;
    }
    leaf SystemConfig_TimeToLive {
      type int32;
    }
    leaf SystemConfig_MsgTxInterval {
      type int32;
    }
    leaf SystemConfig_CDPVersion {
      type cdppb:VersionTypeOptions;
    }
  }
  // core/cdp/cdp.proto
  grouping LocalInfo {
    container LocalInfo_List {
      uses cdppb:LocalInfoEntry;
    }
  }
  // core/cdp/cdp.proto
  grouping LocalInfoEntry {
    container LocalInfoEntry_IdentifyNo {
      uses devicepb:InterfaceIdentify;
    }
    container LocalInfoEntry_PowerAvailable {
      uses cdppb:PowerAvailable;
    }
    container LocalInfoEntry_SystemInfo {
      uses cdppb:SystemInfo;
    }
    container LocalInfoEntry_VoiceVlan {
      uses cdppb:VoiceVLAN;
    }
    container LocalInfoEntry_PortInfo {
      uses cdppb:PortInfo;
    }
    leaf LocalInfoEntry_Capability {
      type cdppb:CapabilityTypeOptions;
    }
  }
  // core/cdp/cdp.proto
  grouping NeighborInfo {
    container NeighborInfo_List {
      uses cdppb:NeighborInfoEntry;
    }
  }
  // core/cdp/cdp.proto
  grouping NeighborInfoEntry {
    container NeighborInfoEntry_IdentifyNo {
      uses cdppb:RecvIdentifyInfo;
    }
    container NeighborInfoEntry_SystemInfo {
      uses cdppb:SystemInfo;
    }
    container NeighborInfoEntry_PowerAvailable {
      uses cdppb:PowerAvailable;
    }
    leaf NeighborInfoEntry_TTL {
      type int64;
    }
    leaf NeighborInfoEntry_VoIPVlan {
      type int32;
    }
  }
  // core/cdp/cdp.proto
  grouping RecvIdentifyInfo {
    container RecvIdentifyInfo_RecvIdentifyNo {
      uses devicepb:InterfaceIdentify;
    }
    leaf RecvIdentifyInfo_PortThroughInterface {
      type string;
    }
    leaf RecvIdentifyInfo_Capability {
      type cdppb:CapabilityTypeOptions;
    }
  }
  // core/cdp/cdp.proto
  grouping SystemInfo {
    leaf SystemInfo_IP {
      type string;
    }
    leaf SystemInfo_DeviceID {
      type string;
    }
    leaf SystemInfo_Platform {
      type string;
    }
    leaf SystemInfo_SystemName {
      type string;
    }
    leaf SystemInfo_SoftwareVersion {
      type string;
    }
    leaf SystemInfo_CDPVersion {
      type cdppb:VersionTypeOptions;
    }
  }
  // core/cdp/cdp.proto
  grouping VoiceVLAN {
    leaf VoiceVLAN_Data {
      type uint8;
    }
    leaf VoiceVLAN_VoiceVlan {
      type int32;
    }
  }
  // core/cdp/cdp.proto
  grouping PortInfo {
    leaf PortInfo_PortThroughInterface {
      type string;
    }
  }
  // core/cdp/cdp.proto
  grouping PowerAvailable {
    leaf PowerAvailable_RequestID {
      type int32;
    }
    leaf PowerAvailable_ManagementID {
      type int32;
    }
    leaf PowerAvailable_Allocated {
      type decimal64 {
        fraction-digits 2;
      }
    }
    leaf PowerAvailable_Supported {
      type decimal64 {
        fraction-digits 2;
      }
    }
  }
  // core/cdp/cdp.proto
  grouping NeighborPoe {
    leaf NeighborPoe_RequestId {
      type int32;
    }
    leaf NeighborPoe_Allocated {
      type decimal64 {
        fraction-digits 2;
      }
    }
  }
  // core/cdp/cdp.proto
  grouping Statistic {
    container Statistic_List {
      uses cdppb:StatisticEntry;
    }
  }
  // core/cdp/cdp.proto
  grouping StatisticEntry {
    container StatisticEntry_IdentifyNo {
      uses devicepb:InterfaceIdentify;
    }
    leaf StatisticEntry_FramesOutV1 {
      type uint64;
    }
    leaf StatisticEntry_FramesOutV2 {
      type uint64;
    }
    leaf StatisticEntry_FramesInV1 {
      type uint64;
    }
    leaf StatisticEntry_FramesInV2 {
      type uint64;
    }
    leaf StatisticEntry_IllegalChecksum {
      type uint64;
    }
    leaf StatisticEntry_OtherErrors {
      type uint64;
    }
  }
}
