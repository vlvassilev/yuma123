submodule intri-common-msg {
  belongs-to "intri-common" {
    prefix "intri-common-msg";
  }

  revision 2022-06-14 {
    description "Build date.";
  }
  // common/common.proto
  grouping Path {
    leaf Path_Path {
      type string;
    }
  }
  // common/common.proto
  grouping ExportPathRequest {
    leaf ExportPathRequest_Path {
      type string;
    }
    leaf ExportPathRequest_FTPSEnabled {
      type boolean;
    }
  }
  // common/common.proto
  grouping ImportPathRequest {
    leaf ImportPathRequest_Path {
      type string;
    }
    leaf ImportPathRequest_FTPSEnabled {
      type boolean;
    }
    leaf ImportPathRequest_RebootAfterAction {
      type boolean;
    }
  }
  // common/common.proto
  grouping Enabled {
    leaf Enabled_IsEnabled {
      type boolean;
    }
  }
  // common/common.proto
  grouping MACAddress {
    leaf MACAddress_MACAddr {
      type string;
    }
  }
  // common/common.proto
  grouping IPAddress {
    leaf IPAddress_IPAddr {
      type string;
    }
  }
  // common/common.proto
  grouping IPv4List {
    leaf IPv4List_List {
      type string;
    }
  }
  // common/common.proto
  grouping IPv6Entry {
    leaf IPv6Entry_Type {
      type IPv6ScopeTypeOptions;
    }
    leaf IPv6Entry_IPAddr {
      type string;
    }
  }
  // common/common.proto
  grouping IPv6List {
    container IPv6List_List {
      uses IPv6Entry;
    }
  }
  // common/common.proto
  grouping Name {
    leaf Name_Name {
      type string;
    }
  }
  // common/common.proto
  grouping NameList {
    leaf NameList_NameList {
      type string;
    }
  }
  // common/common.proto
  grouping Reply {
    leaf Reply_Reply {
      type string;
    }
  }
  // common/common.proto
  grouping Confirm {
    leaf Confirm_Confirm {
      type string;
    }
  }
  // common/common.proto
  grouping DateTime {
    leaf DateTime_Ts {
      type string;
    }
  }
  // common/common.proto
  grouping AllStatus {
    leaf AllStatus_Status {
      type string;
    }
  }
  // common/common.proto
  grouping State {
    leaf State_State {
      type boolean;
    }
  }
  // common/common.proto
  grouping Index {
    leaf Index_Index {
      type int32;
    }
  }
  // common/error.proto
  grouping GRPCErrorDetail {
    leaf GRPCErrorDetail_FieldName {
      type string;
    }
    leaf GRPCErrorDetail_FieldValue {
      type string;
    }
    leaf GRPCErrorDetail_Description {
      type string;
    }
  }
}
