submodule intri-mirroring-enum {
  belongs-to "intri-mirroring" {
    prefix "intri-mirroring-enum";
  }
  revision 2022-06-14 {
    description "Build date.";
  }
  // core/mirroring/mirroring.proto
  typedef DestinationTypeOptions {
    type enumeration {
      enum DESTINATION_TYPE_LOCAL {
        description "[Local] to set SPAN(Local Switched Port Analyzer) destination port interface";
        value 0;
      }
      enum DESTINATION_TYPE_REMOTE {
        description "[Remote] to set RSPAN(Remote SPAN) VLAN";
        value 1;
      }
    }
  }
  // core/mirroring/mirroring.proto
  typedef SourceInterfaceTypeOptions {
    type enumeration {
      enum SOURCE_INTERFACE_TYPE_LOCAL {
        description "[Local] to set SPAN(Local Switched Port Analyzer) source port interface";
        value 0;
      }
      enum SOURCE_INTERFACE_TYPE_VLAN {
        description "*[Internal] to set source port interface";
        value 1;
      }
      enum SOURCE_INTERFACE_TYPE_REMOTE {
        description "[Remote] to set RSPAN(Remote SPAN) VLAN";
        value 2;
      }
    }
  }
  // core/mirroring/mirroring.proto
  typedef DirectionTypeOptions {
    type enumeration {
      enum MIRRORING_DIRECTION_TYPE_NONE {
        description "[None] to disable mirroring direction";
        value 0;
      }
      enum MIRRORING_DIRECTION_TYPE_TX_ONLY {
        description "[TX only] to set mirroring direction TX only";
        value 1;
      }
      enum MIRRORING_DIRECTION_TYPE_RX_ONLY {
        description "[RX only] to set mirroring direction RX only";
        value 2;
      }
      enum MIRRORING_DIRECTION_TYPE_BOTH {
        description "[TX+RX] to set mirroring direction TX and RX both";
        value 3;
      }
    }
  }
}
