module intri-timestamp {

  namespace "intri:intri-timestamp";
  prefix "intri-timestamp";
  organization "
    Intrising Inc.";
  contact "
    intrising@intrising.com.tw";
  revision 2022-06-24 {
    description "Build date.";
  }

  grouping Timestamp {
    leaf Seconds {
      mandatory "true";
      type int64;
    }
    leaf Nanos {
      mandatory "true";
      type int32;
    }
  }
}
