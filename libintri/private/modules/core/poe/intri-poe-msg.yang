submodule intri-poe-msg {
  belongs-to "intri-poe" {
    prefix "intri-poe-msg";
  }
  include intri-poe-enum;
  import poepb {
    prefix "poepb";
  }
  import devicepb {
    prefix "devicepb";
  }
  import hardwarepb {
    prefix "hardwarepb";
  }
  revision 2022-06-14 {
    description "Build date.";
  }
  // core/poe/poe.proto
  grouping Config {
    container Config_Budget {
      uses poepb:SystemBudget;
    }
    container Config_Port {
      uses poepb:PortConfig;
    }
  }
  // core/poe/poe.proto
  grouping SystemBudget {
    leaf SystemBudget_MaxPowerAvailable {
      type int32;
    }
  }
  // core/poe/poe.proto
  grouping PortConfig {
    container PortConfig_List {
      uses poepb:ConfigEntry;
    }
  }
  // core/poe/poe.proto
  grouping ConfigEntry {
    container ConfigEntry_IdentifyNo {
      uses devicepb:InterfaceIdentify;
    }
    leaf ConfigEntry_Enabled {
      type boolean;
    }
    leaf ConfigEntry_Mode {
      type hardwarepb:PoEPortModeTypeOptions;
    }
    leaf ConfigEntry_Priority {
      type hardwarepb:PoEPriorityLevelTypeOptions;
    }
  }
  // core/poe/poe.proto
  grouping SystemStatus {
    leaf SystemStatus_MinShutDownVoltage {
      type decimal64 {
        fraction-digits 2;
      }
    }
    leaf SystemStatus_MaxShutDownVoltage {
      type decimal64 {
        fraction-digits 2;
      }
    }
    leaf SystemStatus_VMainVoltage {
      type decimal64 {
        fraction-digits 2;
      }
    }
    leaf SystemStatus_IMainCurrent {
      type decimal64 {
        fraction-digits 2;
      }
    }
    leaf SystemStatus_PowerConsumption {
      type decimal64 {
        fraction-digits 2;
      }
    }
  }
  // core/poe/poe.proto
  grouping PortStatus {
    container PortStatus_List {
      uses poepb:PortStatusEntry;
    }
  }
  // core/poe/poe.proto
  grouping PortStatusEntry {
    container PortStatusEntry_IdentifyNo {
      uses devicepb:InterfaceIdentify;
    }
    leaf PortStatusEntry_Condition {
      type hardwarepb:PoEConditionTypeOptions;
    }
    leaf PortStatusEntry_DeterminedClass {
      type hardwarepb:PoEDeterminedClassTypeOptions;
    }
    leaf PortStatusEntry_Priority {
      type hardwarepb:PoEPriorityLevelTypeOptions;
    }
    leaf PortStatusEntry_OutputCurrent {
      type decimal64 {
        fraction-digits 2;
      }
    }
    leaf PortStatusEntry_OutputVoltage {
      type decimal64 {
        fraction-digits 2;
      }
    }
    leaf PortStatusEntry_OutputPower {
      type decimal64 {
        fraction-digits 2;
      }
    }
    leaf PortStatusEntry_SupportMaxPower {
      type decimal64 {
        fraction-digits 2;
      }
    }
  }
  // core/poe/poe.proto
  grouping SetPoEMaxPowerAvailableRequest {
    leaf SetPoEMaxPowerAvailableRequest_MaxPowerAvailable {
      type int32;
    }
  }
}
