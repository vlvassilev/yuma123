submodule intri-multicast-msg {
  belongs-to "intri-multicast" {
    prefix "intri-multicast-msg";
  }
  include intri-multicast-enum;
  import multicastpb {
    prefix "multicastpb";
  }
  import devicepb {
    prefix "devicepb";
  }
  revision 2022-06-14 {
    description "Build date.";
  }
  // core/multicast/multicast.proto
  grouping Config {
    leaf Config_IGMPSnoopingGlobalEnabled {
      type boolean;
    }
    leaf Config_MLDSnoopingGlobalEnabled {
      type boolean;
    }
    container Config_IGMPConfig {
      uses multicastpb:Snooping;
    }
    container Config_MLDConfig {
      uses multicastpb:Snooping;
    }
    container Config_RouterConfig {
      uses multicastpb:RouterPort;
    }
    container Config_UnregisterConfig {
      uses multicastpb:UnregisterFlood;
    }
    container Config_StaticGroups {
      uses multicastpb:Static;
    }
  }
  // core/multicast/multicast.proto
  grouping Snooping {
    container Snooping_VlanList {
      uses multicastpb:SnoopingConfigEntry;
    }
  }
  // core/multicast/multicast.proto
  grouping SnoopingConfigEntry {
    leaf SnoopingConfigEntry_VlanID {
      type int32;
    }
    leaf SnoopingConfigEntry_SnoopingEnabled {
      type boolean;
    }
    leaf SnoopingConfigEntry_QuerierVersion {
      type multicastpb:VersionTypeOptions;
    }
    leaf SnoopingConfigEntry_MulticastRouterDetection {
      type multicastpb:RouterDetectionTypeOptions;
    }
    leaf SnoopingConfigEntry_EnableFastLeave {
      type boolean;
    }
    leaf SnoopingConfigEntry_EnableReportSuppression {
      type boolean;
    }
    leaf SnoopingConfigEntry_GroupLimit {
      type int32;
    }
    leaf SnoopingConfigEntry_GroupMembershipInterval {
      type int32;
    }
    leaf SnoopingConfigEntry_LastMemberQueryTime {
      type int32;
    }
    leaf SnoopingConfigEntry_MaxResponseTime {
      type int32;
    }
    leaf SnoopingConfigEntry_RouterAgingTime {
      type int32;
    }
    leaf SnoopingConfigEntry_StartQueryCount {
      type int32;
    }
    leaf SnoopingConfigEntry_StartQueryInterval {
      type int32;
    }
    leaf SnoopingConfigEntry_QueryInterval {
      type int32;
    }
    leaf SnoopingConfigEntry_Robustness {
      type int32;
    }
    container SnoopingConfigEntry_IdentifyiesConfig {
      uses multicastpb:PortEnabledEntry;
    }
  }
  // core/multicast/multicast.proto
  grouping UnregisterFlood {
    container UnregisterFlood_VlanList {
      uses multicastpb:UnregisterFloodVlan;
    }
  }
  // core/multicast/multicast.proto
  grouping UnregisterFloodVlan {
    leaf UnregisterFloodVlan_VlanID {
      type int32;
    }
    leaf UnregisterFloodVlan_Enabled {
      type boolean;
    }
  }
  // core/multicast/multicast.proto
  grouping RouterPort {
    container RouterPort_VlanList {
      uses multicastpb:RouterPortVlanEntry;
    }
  }
  // core/multicast/multicast.proto
  grouping RouterPortVlanEntry {
    leaf RouterPortVlanEntry_VlanID {
      type int32;
    }
    container RouterPortVlanEntry_PortList {
      uses multicastpb:PortEnabledEntry;
    }
  }
  // core/multicast/multicast.proto
  grouping PortEnabledEntry {
    container PortEnabledEntry_IdentifyNo {
      uses devicepb:InterfaceIdentify;
    }
    leaf PortEnabledEntry_Enabled {
      type boolean;
    }
  }
  // core/multicast/multicast.proto
  grouping Static {
    container Static_List {
      uses multicastpb:StaticGroupsConfigEntry;
    }
  }
  // core/multicast/multicast.proto
  grouping StaticGroupsConfigEntry {
    leaf StaticGroupsConfigEntry_VlanID {
      type int32;
    }
    leaf StaticGroupsConfigEntry_Name {
      type string;
    }
    leaf StaticGroupsConfigEntry_MulticastAddress {
      type string;
    }
    container StaticGroupsConfigEntry_ForwardingPort {
      uses devicepb:PortList;
    }
  }
  // core/multicast/multicast.proto
  grouping IGMPStatistics {
    container IGMPStatistics_List {
      uses multicastpb:IGMPStatisticEntry;
    }
  }
  // core/multicast/multicast.proto
  grouping IGMPStatisticEntry {
    leaf IGMPStatisticEntry_VlanID {
      type int32;
    }
    leaf IGMPStatisticEntry_RxGeneralQueries {
      type int32;
    }
    leaf IGMPStatisticEntry_RxV3Reports {
      type int32;
    }
    leaf IGMPStatisticEntry_RxV2Reports {
      type int32;
    }
    leaf IGMPStatisticEntry_RxV2Leaves {
      type int32;
    }
    leaf IGMPStatisticEntry_RxV1Reports {
      type int32;
    }
    leaf IGMPStatisticEntry_Querier {
      type boolean;
    }
  }
  // core/multicast/multicast.proto
  grouping RouterStatus {
    container RouterStatus_VlanList {
      uses multicastpb:RouterStatusEntry;
    }
  }
  // core/multicast/multicast.proto
  grouping RouterStatusEntry {
    leaf RouterStatusEntry_VlanID {
      type int32;
    }
    container RouterStatusEntry_List {
      uses multicastpb:RouterPortStatusEntry;
    }
  }
  // core/multicast/multicast.proto
  grouping RouterPortStatusEntry {
    leaf RouterPortStatusEntry_Type {
      type multicastpb:ProtocolTypeOptions;
    }
    leaf RouterPortStatusEntry_Status {
      type multicastpb:RouterStatusTypeOptions;
    }
    container RouterPortStatusEntry_IdentifyNo {
      uses devicepb:InterfaceIdentify;
    }
  }
  // core/multicast/multicast.proto
  grouping DynamicGroups {
    container DynamicGroups_List {
      uses multicastpb:DynamicGroupEntry;
    }
  }
  // core/multicast/multicast.proto
  grouping DynamicGroupEntry {
    leaf DynamicGroupEntry_VlanID {
      type int32;
    }
    leaf DynamicGroupEntry_Address {
      type string;
    }
    leaf DynamicGroupEntry_TTL {
      type int32;
    }
    container DynamicGroupEntry_IdentifyList {
      uses devicepb:InterfaceIdentify;
    }
  }
  // core/multicast/multicast.proto
  grouping MLDStatistics {
    container MLDStatistics_List {
      uses multicastpb:MLDStatisticEntry;
    }
  }
  // core/multicast/multicast.proto
  grouping MLDStatisticEntry {
    leaf MLDStatisticEntry_VlanID {
      type int32;
    }
    leaf MLDStatisticEntry_RxGeneralQueries {
      type int32;
    }
    leaf MLDStatisticEntry_RxV2Reports {
      type int32;
    }
    leaf MLDStatisticEntry_RxV1Reports {
      type int32;
    }
    leaf MLDStatisticEntry_RxV1Leaves {
      type int32;
    }
    leaf MLDStatisticEntry_Querier {
      type boolean;
    }
  }
  // core/multicast/multicast.proto
  grouping VlanList {
    leaf VlanList_List {
      type int32;
    }
  }
}
