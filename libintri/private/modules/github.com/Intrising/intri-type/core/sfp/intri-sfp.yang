// Code generated by protoc-gen-yang. DO NOT EDIT.


/* ****************************************************************************************************
 * Import Path : "github.com/Intrising/intri-type/core/sfp"                                           *
 * Dir Path    : github.com/Intrising/intri-type/core/sfp                                             *
 * Go Package  : sfp                                                                                  *
 * Files       : 2                                                                                    *
 **************************************************************************************************** */
module intri-sfp {

  namespace "intri:intri-sfp";

  prefix "intri-sfp";

  organization "Intrising Inc.";

  contact "intrising@intrising.com.tw";

  revision 2022-06-23 {
    description "Build date.";
  }

  import intri-event {
    prefix intri-event;
  }
  import intri-empty {
    prefix intri-empty;
  }


  /* **************************************************************************************************
   * Msgs        : 2                                                                                  *
   ************************************************************************************************** */
  /* core/sfp/sfp.proto */
  grouping Config {
    leaf LossOfSignalEvent {
      type boolean;
    }
  }
  /* core/sfp/sfp.proto */
  grouping Info {
    container List {
      list List_Entry {
        uses intri-event:SFPInfo;
      }
    }
  }


  /* **************************************************************************************************
   * Services    : 1                                                                                  *
   ************************************************************************************************** */

  /* **************************************************************************************************
   * Service     : SFP                                                                                *
   * Methods     : 3                                                                                  *
   ************************************************************************************************** */
  /* core/sfp/service.proto */
  rpc intri-sfp-GetConfig {
    output  {
      uses Config;
    }
  }
  /* core/sfp/service.proto */
  rpc intri-sfp-SetConfig {
    input  {
      uses Config;
    }
  }
  /* core/sfp/service.proto */
  rpc intri-sfp-GetStatus {
    output  {
      uses Info;
    }
  }

}
