module intri-access {
  namespace "intri:intri-access";
  prefix "intri-access";
  import accesspb {
    prefix "accesspb";
  }
  organization "Intrising Inc.";
  contact "xxx@intrising.com.tw";
  revision 2022-06-14 {
    description "Build date.";
  }
}
