module intri-snmp {

  namespace "intri:intri-snmp";
  prefix "intri-snmp";
  organization "
    Intrising Inc.";
  contact "
    intrising@intrising.com.tw";
  revision 2022-06-24 {
    description "Build date.";
  }

  grouping EngineInfo {
    leaf Boots {
      mandatory "true";
      type int32;
    }
    leaf RunTime {
      mandatory "true";
      type int64;
    }
  }
}
