module intri-fdb {
  namespace "intri:intri-fdb";
  prefix "intri-fdb";
  import fdbpb {
    prefix "fdbpb";
  }
  organization "Intrising Inc.";
  contact "xxx@intrising.com.tw";
  revision 2022-06-14 {
    description "Build date.";
  }
}
