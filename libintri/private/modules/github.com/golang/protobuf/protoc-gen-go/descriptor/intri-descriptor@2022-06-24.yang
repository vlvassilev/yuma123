// Code generated by protoc-gen-yang. DO NOT EDIT.


/* ****************************************************************************************************
 * Import Path : "github.com/golang/protobuf/protoc-gen-go/descriptor"                                *
 * Dir Path    : github.com/golang/protobuf/protoc-gen-go/descriptor                                  *
 * Go Package  : descriptor                                                                           *
 * Files       : 1                                                                                    *
 **************************************************************************************************** */
module intri-descriptor {

  namespace "intri:intri-descriptor";

  prefix "intri-descriptor";

  organization "
    Intrising Inc.";

  contact "
    intrising@intrising.com.tw";

  revision 2022-06-24 {
    description "Build date.";
  }


  /* **************************************************************************************************
   * Msgs        : 21                                                                                 *
   ************************************************************************************************** */
  /* google/protobuf/descriptor.proto */
  grouping FileDescriptorSet {
    container File {
      list File_Entry {
        uses FileDescriptorProto;
      }
    }
  }
  /* google/protobuf/descriptor.proto */
  grouping FileDescriptorProto {
    leaf Name {
      type string;
    }
    leaf Package {
      type string;
    }
    container Dependency {
      leaf-list Dependency_Entry {
        type string;
      }
    }
    container PublicDependency {
      leaf-list PublicDependency_Entry {
        type int32;
      }
    }
    container WeakDependency {
      leaf-list WeakDependency_Entry {
        type int32;
      }
    }
    container MessageType {
      list MessageType_Entry {
        uses DescriptorProto;
      }
    }
    container EnumType {
      list EnumType_Entry {
        uses EnumDescriptorProto;
      }
    }
    container Service {
      list Service_Entry {
        uses ServiceDescriptorProto;
      }
    }
    container Extension {
      list Extension_Entry {
        uses FieldDescriptorProto;
      }
    }
    container Options {
      uses FileOptions;
    }
    container SourceCodeInfo {
      uses SourceCodeInfo;
    }
    leaf Syntax {
      type string;
    }
  }
  /* google/protobuf/descriptor.proto */
  grouping DescriptorProto {
    leaf Name {
      type string;
    }
    container Field {
      list Field_Entry {
        uses FieldDescriptorProto;
      }
    }
    container Extension {
      list Extension_Entry {
        uses FieldDescriptorProto;
      }
    }
    container NestedType {
      list NestedType_Entry {
        uses DescriptorProto;
      }
    }
    container EnumType {
      list EnumType_Entry {
        uses EnumDescriptorProto;
      }
    }
    container ExtensionRange {
      list ExtensionRange_Entry {
        uses DescriptorProto_ExtensionRange;
      }
    }
    container OneofDecl {
      list OneofDecl_Entry {
        uses OneofDescriptorProto;
      }
    }
    container Options {
      uses MessageOptions;
    }
    container ReservedRange {
      list ReservedRange_Entry {
        uses DescriptorProto_ReservedRange;
      }
    }
    container ReservedName {
      leaf-list ReservedName_Entry {
        type string;
      }
    }
  }
  /* google/protobuf/descriptor.proto */
  grouping ExtensionRangeOptions {
    container UninterpretedOption {
      list UninterpretedOption_Entry {
        uses UninterpretedOption;
      }
    }
  }
  /* google/protobuf/descriptor.proto */
  grouping FieldDescriptorProto {
    leaf Name {
      type string;
    }
    leaf Number {
      type int32;
    }
    leaf Label {
      type FieldDescriptorProto_Label;
    }
    leaf Type {
      type FieldDescriptorProto_Type;
    }
    leaf TypeName {
      type string;
    }
    leaf Extendee {
      type string;
    }
    leaf DefaultValue {
      type string;
    }
    leaf OneofIndex {
      type int32;
    }
    leaf JsonName {
      type string;
    }
    container Options {
      uses FieldOptions;
    }
  }
  /* google/protobuf/descriptor.proto */
  grouping OneofDescriptorProto {
    leaf Name {
      type string;
    }
    container Options {
      uses OneofOptions;
    }
  }
  /* google/protobuf/descriptor.proto */
  grouping EnumDescriptorProto {
    leaf Name {
      type string;
    }
    container Value {
      list Value_Entry {
        uses EnumValueDescriptorProto;
      }
    }
    container Options {
      uses EnumOptions;
    }
    container ReservedRange {
      list ReservedRange_Entry {
        uses EnumDescriptorProto_EnumReservedRange;
      }
    }
    container ReservedName {
      leaf-list ReservedName_Entry {
        type string;
      }
    }
  }
  /* google/protobuf/descriptor.proto */
  grouping EnumValueDescriptorProto {
    leaf Name {
      type string;
    }
    leaf Number {
      type int32;
    }
    container Options {
      uses EnumValueOptions;
    }
  }
  /* google/protobuf/descriptor.proto */
  grouping ServiceDescriptorProto {
    leaf Name {
      type string;
    }
    container Method {
      list Method_Entry {
        uses MethodDescriptorProto;
      }
    }
    container Options {
      uses ServiceOptions;
    }
  }
  /* google/protobuf/descriptor.proto */
  grouping MethodDescriptorProto {
    leaf Name {
      type string;
    }
    leaf InputType {
      type string;
    }
    leaf OutputType {
      type string;
    }
    container Options {
      uses MethodOptions;
    }
    leaf ClientStreaming {
      type boolean;
    }
    leaf ServerStreaming {
      type boolean;
    }
  }
  /* google/protobuf/descriptor.proto */
  grouping FileOptions {
    leaf JavaPackage {
      type string;
    }
    leaf JavaOuterClassname {
      type string;
    }
    leaf JavaMultipleFiles {
      type boolean;
    }
    leaf JavaGenerateEqualsAndHash {
      type boolean;
    }
    leaf JavaStringCheckUtf8 {
      type boolean;
    }
    leaf OptimizeFor {
      type FileOptions_OptimizeMode;
    }
    leaf GoPackage {
      type string;
    }
    leaf CcGenericServices {
      type boolean;
    }
    leaf JavaGenericServices {
      type boolean;
    }
    leaf PyGenericServices {
      type boolean;
    }
    leaf PhpGenericServices {
      type boolean;
    }
    leaf Deprecated {
      type boolean;
    }
    leaf CcEnableArenas {
      type boolean;
    }
    leaf ObjcClassPrefix {
      type string;
    }
    leaf CsharpNamespace {
      type string;
    }
    leaf SwiftPrefix {
      type string;
    }
    leaf PhpClassPrefix {
      type string;
    }
    leaf PhpNamespace {
      type string;
    }
    leaf PhpMetadataNamespace {
      type string;
    }
    leaf RubyPackage {
      type string;
    }
    container UninterpretedOption {
      list UninterpretedOption_Entry {
        uses UninterpretedOption;
      }
    }
  }
  /* google/protobuf/descriptor.proto */
  grouping MessageOptions {
    leaf MessageSetWireFormat {
      type boolean;
    }
    leaf NoStandardDescriptorAccessor {
      type boolean;
    }
    leaf Deprecated {
      type boolean;
    }
    leaf MapEntry {
      type boolean;
    }
    container UninterpretedOption {
      list UninterpretedOption_Entry {
        uses UninterpretedOption;
      }
    }
  }
  /* google/protobuf/descriptor.proto */
  grouping FieldOptions {
    leaf Ctype {
      type FieldOptions_CType;
    }
    leaf Packed {
      type boolean;
    }
    leaf Jstype {
      type FieldOptions_JSType;
    }
    leaf Lazy {
      type boolean;
    }
    leaf Deprecated {
      type boolean;
    }
    leaf Weak {
      type boolean;
    }
    container UninterpretedOption {
      list UninterpretedOption_Entry {
        uses UninterpretedOption;
      }
    }
  }
  /* google/protobuf/descriptor.proto */
  grouping OneofOptions {
    container UninterpretedOption {
      list UninterpretedOption_Entry {
        uses UninterpretedOption;
      }
    }
  }
  /* google/protobuf/descriptor.proto */
  grouping EnumOptions {
    leaf AllowAlias {
      type boolean;
    }
    leaf Deprecated {
      type boolean;
    }
    container UninterpretedOption {
      list UninterpretedOption_Entry {
        uses UninterpretedOption;
      }
    }
  }
  /* google/protobuf/descriptor.proto */
  grouping EnumValueOptions {
    leaf Deprecated {
      type boolean;
    }
    container UninterpretedOption {
      list UninterpretedOption_Entry {
        uses UninterpretedOption;
      }
    }
  }
  /* google/protobuf/descriptor.proto */
  grouping ServiceOptions {
    leaf Deprecated {
      type boolean;
    }
    container UninterpretedOption {
      list UninterpretedOption_Entry {
        uses UninterpretedOption;
      }
    }
  }
  /* google/protobuf/descriptor.proto */
  grouping MethodOptions {
    leaf Deprecated {
      type boolean;
    }
    leaf IdempotencyLevel {
      type MethodOptions_IdempotencyLevel;
    }
    container UninterpretedOption {
      list UninterpretedOption_Entry {
        uses UninterpretedOption;
      }
    }
  }
  /* google/protobuf/descriptor.proto */
  grouping UninterpretedOption {
    container Name {
      list Name_Entry {
        uses UninterpretedOption_NamePart;
      }
    }
    leaf IdentifierValue {
      type string;
    }
    leaf PositiveIntValue {
      type uint64;
    }
    leaf NegativeIntValue {
      type int64;
    }
    leaf DoubleValue {
      type decimal64 {
        fraction-digits 2;
      }
    }
    leaf StringValue {
      type uint8;
    }
    leaf AggregateValue {
      type string;
    }
  }
  /* google/protobuf/descriptor.proto */
  grouping SourceCodeInfo {
    container Location {
      list Location_Entry {
        uses SourceCodeInfo_Location;
      }
    }
  }
  /* google/protobuf/descriptor.proto */
  grouping GeneratedCodeInfo {
    container Annotation {
      list Annotation_Entry {
        uses GeneratedCodeInfo_Annotation;
      }
    }
  }

}
