// Code generated by protoc-gen-yang. DO NOT EDIT.


/* ****************************************************************************************************
 * Import Path : "github.com/Intrising/intri-type/cli"                                                *
 * Dir Path    : github.com/Intrising/intri-type/cli                                                  *
 * Go Package  : cli                                                                                  *
 * Files       : 2                                                                                    *
 **************************************************************************************************** */
module intri-cli {

  namespace "intri:intri-cli";

  prefix "intri-cli";

  organization "Intrising Inc.";

  contact "intrising@intrising.com.tw";

  revision 2022-06-23 {
    description "Build date.";
  }

  import intri-userinterface {
    prefix intri-userinterface;
  }
  import intri-empty {
    prefix intri-empty;
  }


  /* **************************************************************************************************
   * Msgs        : 1                                                                                  *
   ************************************************************************************************** */
  /* cli/cli.proto */
  grouping ScriptAction {
    leaf Token {
      type string;
    }
    leaf FileURL {
      type string;
    }
    leaf IsFTPS {
      type boolean;
    }
    leaf ForceTFTP {
      type boolean;
    }
  }


  /* **************************************************************************************************
   * Services    : 1                                                                                  *
   ************************************************************************************************** */

  /* **************************************************************************************************
   * Service     : CLI                                                                                *
   * Methods     : 2                                                                                  *
   ************************************************************************************************** */
  /* cli/service.proto */
  rpc intri-cli-SetConfig {
    input  {
      uses intri-userinterface:CLIConfig;
    }
  }
  /* cli/service.proto */
  rpc intri-cli-RunScript {
    input  {
      uses ScriptAction;
    }
  }

}
