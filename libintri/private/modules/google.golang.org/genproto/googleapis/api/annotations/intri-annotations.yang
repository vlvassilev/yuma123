// Code generated by protoc-gen-yang. DO NOT EDIT.


/* ****************************************************************************************************
 * Import Path : "google.golang.org/genproto/googleapis/api/annotations"                              *
 * Dir Path    : google.golang.org/genproto/googleapis/api/annotations                                *
 * Go Package  : annotations                                                                          *
 * Files       : 2                                                                                    *
 **************************************************************************************************** */
module intri-annotations {

  namespace "intri:intri-annotations";

  prefix "intri-annotations";

  organization "Intrising Inc.";

  contact "intrising@intrising.com.tw";

  revision 2022-06-23 {
    description "Build date.";
  }


  /* **************************************************************************************************
   * Msgs        : 3                                                                                  *
   ************************************************************************************************** */
  /* google/api/http.proto */
  grouping Http {
    container Rules {
      list Rules_Entry {
        uses HttpRule;
      }
    }
    leaf FullyDecodeReservedExpansion {
      type boolean;
    }
  }
  /* google/api/http.proto */
  grouping HttpRule {
    leaf Selector {
      type string;
    }
    choice Pattern {
      leaf Get {
        type string;
      }
      leaf Put {
        type string;
      }
      leaf Post {
        type string;
      }
      leaf Delete {
        type string;
      }
      leaf Patch {
        type string;
      }
      container Custom {
        uses CustomHttpPattern;
      }
    }
    leaf Body {
      type string;
    }
    leaf ResponseBody {
      type string;
    }
    container AdditionalBindings {
      list AdditionalBindings_Entry {
        uses HttpRule;
      }
    }
  }
  /* google/api/http.proto */
  grouping CustomHttpPattern {
    leaf Kind {
      type string;
    }
    leaf Path {
      type string;
    }
  }

}
