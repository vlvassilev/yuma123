submodule intri-sfp-msg {
  belongs-to "intri-sfp" {
    prefix "intri-sfp-msg";
  }
  include intri-sfp-enum;
  import eventpb {
    prefix "eventpb";
  }
  revision 2022-06-14 {
    description "Build date.";
  }
  // core/sfp/sfp.proto
  grouping Config {
    leaf Config_LossOfSignalEvent {
      type boolean;
    }
  }
  // core/sfp/sfp.proto
  grouping Info {
    container Info_List {
      uses eventpb:SFPInfo;
    }
  }
}
