module sercom-portsecurity {

  namespace "sercom:sercom-portsecurity";
  prefix "sercom-portsecurity";
  organization "
    Sercomm Inc.";
  contact "
    sercomm@sercomm.com.tw";
  revision 2022-06-24 {
    description "Build date.";
  }

  import sercom-device {
    prefix sercom-device;
  }
  import sercom-empty {
    prefix sercom-empty;
  }
  typedef PortSecurityModeTypeOptions {
    type enumeration {
      enum PORT_SECURITY_MODE_TYPE_STATIC {
        description "[Static]";
        value 0;
      }
      enum PORT_SECURITY_MODE_TYPE_STICKY {
        description "[Sticky]";
        value 1;
      }
      enum PORT_SECURITY_MODE_TYPE_DYNAMIC {
        description "[Dynamic]";
        value 2;
      }
    }
  }
  typedef PortSecurityAgeModeTypeOptions {
    type enumeration {
      enum PORT_SECURITY_AGE_MODE_TYPE_ABSOULTE {
        description "[Absolute] Absolute aging";
        value 0;
      }
      enum PORT_SECURITY_AGE_MODE_TYPE_INACTIVITY {
        description "[Inactivity] Aging based on inactivity time period";
        value 1;
      }
    }
  }
  typedef PortSecurityViolationTypeOptions {
    type enumeration {
      enum PORT_SECURITY_VIOLATION_TYPE_SHUTDOWN {
        description "[Shutdown] Security violation shutdown mode";
        value 0;
      }
      enum PORT_SECURITY_VIOLATION_TYPE_DISCARD {
        description "[Discard] Security violation discard mode";
        value 1;
      }
      enum PORT_SECURITY_VIOLATION_TYPE_RESTRICT {
        description "[Restrict] Security violation restrict mode";
        value 2;
      }
    }
  }
  typedef PortSecurityStatusTypeOptions {
    type enumeration {
      enum PORT_SECURITY_STATUS_TYPE_SECURE_DOWN {
        description "[Secure-Down]";
        value 0;
      }
      enum PORT_SECURITY_STATUS_TYPE_SECURE_UP {
        description "[Secure-Up]";
        value 1;
      }
      enum PORT_SECURITY_STATUS_TYPE_SECURE_SHUTDOWN {
        description "[Secure-Shutdown]";
        value 2;
      }
    }
  }
  grouping Config {
    container List {
      list List_Entry {
        uses PortSecurityConfigEntry;
      }
    }
  }
  grouping PortSecurityConfigEntry {
    container IdentifyNo {
      uses sercom-device:InterfaceIdentify;
    }
    leaf Enabled {
      mandatory "true";
      type boolean;
    }
    leaf Mode {
      mandatory "true";
      type PortSecurityModeTypeOptions;
    }
    leaf MaxMACCount {
      mandatory "true";
      type int32;
    }
    container SecureAddressList {
      list SecureAddressList_Entry {
        uses SecureEntry;
      }
    }
    leaf ViolationMode {
      mandatory "true";
      type PortSecurityViolationTypeOptions;
    }
  }
  grouping SecureEntry {
    leaf VlanID {
      mandatory "true";
      type int32;
    }
    leaf MACAddress {
      mandatory "true";
      type string;
    }
  }
  grouping PortSecureEntry {
    container IdentifyNo {
      uses sercom-device:InterfaceIdentify;
    }
    container Entry {
      uses SecureEntry;
    }
  }
  grouping Status {
    container List {
      list List_Entry {
        uses PortSecurityStatusEntry;
      }
    }
  }
  grouping PortSecurityStatusEntry {
    container IdentifyNo {
      uses sercom-device:InterfaceIdentify;
    }
    leaf Enabled {
      mandatory "true";
      type boolean;
    }
    leaf Status {
      mandatory "true";
      type PortSecurityStatusTypeOptions;
    }
    leaf ViolationMode {
      mandatory "true";
      type PortSecurityViolationTypeOptions;
    }
    leaf MaxMACCount {
      mandatory "true";
      type int32;
    }
    leaf SecureMACCount {
      mandatory "true";
      type int32;
    }
    leaf LastSourceMACaddressVlan {
      mandatory "true";
      type string;
    }
  }
  grouping PortSecurityAge {
    leaf StaticAging {
      mandatory "true";
      type boolean;
    }
    leaf Type {
      mandatory "true";
      type PortSecurityAgeModeTypeOptions;
    }
    leaf Time {
      mandatory "true";
      type int32;
    }
  }
  rpc sercom-portsecurity-PortSecurity-GetConfig {
    output {
      uses Config;
    }
  }
  rpc sercom-portsecurity-PortSecurity-UpdatePortSecurityConfig {
    input {
      uses PortSecurityConfigEntry;
    }
  }
  rpc sercom-portsecurity-PortSecurity-AddPortSecureEntry {
    input {
      uses PortSecureEntry;
    }
  }
  rpc sercom-portsecurity-PortSecurity-DeletePortSecureEntry {
    input {
      uses PortSecureEntry;
    }
  }
  rpc sercom-portsecurity-PortSecurity-GetPortSecurityInfo {
    output {
      uses Status;
    }
  }
}
