module intri-duration {

  namespace "intri:intri-duration";
  prefix "intri-duration";
  organization "
    Intrising Inc.";
  contact "
    intrising@intrising.com.tw";
  revision 2022-06-24 {
    description "Build date.";
  }

  grouping Duration {
    leaf Seconds {
      mandatory "true";
      type int64;
    }
    leaf Nanos {
      mandatory "true";
      type int32;
    }
  }
}
