module intri-udld {
  namespace "intri:intri-udld";
  prefix "intri-udld";
  import udldpb {
    prefix "udldpb";
  }
  organization "Intrising Inc.";
  contact "xxx@intrising.com.tw";
  revision 2022-06-14 {
    description "Build date.";
  }
}
