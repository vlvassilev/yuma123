// Code generated by protoc-gen-yang. DO NOT EDIT.


/* ****************************************************************************************************
 * Import Path : "github.com/Intrising/intri-type/core/multicast"                                     *
 * Dir Path    : github.com/Intrising/intri-type/core/multicast                                       *
 * Go Package  : multicast                                                                            *
 * Files       : 3                                                                                    *
 **************************************************************************************************** */
module intri-multicast {

  namespace "intri:intri-multicast";

  prefix "intri-multicast";

  organization "Intrising Inc.";

  contact "intrising@intrising.com.tw";

  revision 2022-06-23 {
    description "Build date.";
  }

  import intri-device {
    prefix intri-device;
  }
  import intri-empty {
    prefix intri-empty;
  }
  import intri-common {
    prefix intri-common;
  }


  /* **************************************************************************************************
   * Enums       : 5                                                                                  *
   ************************************************************************************************** */
  /* core/multicast/common.proto */
  typedef RouterDetectionTypeOptions {
    type enumeration {
      enum ROUTER_DETECTION_TYPE_QUERY_MESSAGE {
        description "[Query Message]";
        value 0;
      }
    }
  }
  /* core/multicast/common.proto */
  typedef ProtocolTypeOptions {
    type enumeration {
      enum PROTOCOL_TYPE_NONE {
        description "[NONE]";
        value 0;
      }
      enum PROTOCOL_TYPE_IGMP {
        description "[IGMP]";
        value 1;
      }
      enum PROTOCOL_TYPE_MLD {
        description "[MLD]";
        value 2;
      }
      enum PROTOCOL_TYPE_BOTH {
        description "[BOTH]";
        value 3;
      }
    }
  }
  /* core/multicast/common.proto */
  typedef RouterStatusTypeOptions {
    type enumeration {
      enum ROUTER_STATUS_TYPE_DISABLED {
        description "[Disabled]";
        value 0;
      }
      enum ROUTER_STATUS_TYPE_DYNAMIC {
        description "[Dynamic]";
        value 1;
      }
      enum ROUTER_STATUS_TYPE_STATIC {
        description "[Static]";
        value 2;
      }
      enum ROUTER_STATUS_TYPE_BOTH {
        description "[Both]";
        value 3;
      }
    }
  }
  /* core/multicast/common.proto */
  typedef VersionTypeOptions {
    type enumeration {
      enum VERSION_TYPE_IGMP_V1 {
        description "[IGMP V1]";
        value 0;
      }
      enum VERSION_TYPE_IGMP_V2 {
        description "[IGMP V2]";
        value 1;
      }
      enum VERSION_TYPE_IGMP_V3 {
        description "[IGMP V3]";
        value 2;
      }
      enum VERSION_TYPE_MLD_V1 {
        description "[MLD V1]";
        value 3;
      }
      enum VERSION_TYPE_MLD_V2 {
        description "[MLD V2]";
        value 4;
      }
      enum VERSION_TYPE_DISABLED {
        description "[Disabled]";
        value 5;
      }
    }
  }
  /* core/multicast/common.proto */
  typedef StaticTypeOptions {
    type enumeration {
      enum STATIC_TYPE_L2 {
        description "[L2]";
        value 0;
      }
      enum STATIC_TYPE_L3 {
        description "[L3]";
        value 1;
      }
    }
  }


  /* **************************************************************************************************
   * Msgs        : 20                                                                                 *
   ************************************************************************************************** */
  /* core/multicast/multicast.proto */
  grouping Config {
    leaf IGMPSnoopingGlobalEnabled {
      type boolean;
    }
    leaf MLDSnoopingGlobalEnabled {
      type boolean;
    }
    container IGMPConfig {
      uses Snooping;
    }
    container MLDConfig {
      uses Snooping;
    }
    container RouterConfig {
      uses RouterPort;
    }
    container UnregisterConfig {
      uses UnregisterFlood;
    }
    container StaticGroups {
      uses Static;
    }
  }
  /* core/multicast/multicast.proto */
  grouping Snooping {
    container VlanList {
      list VlanList_Entry {
        uses SnoopingConfigEntry;
      }
    }
  }
  /* core/multicast/multicast.proto */
  grouping SnoopingConfigEntry {
    leaf VlanID {
      type int32;
    }
    leaf SnoopingEnabled {
      type boolean;
    }
    leaf QuerierVersion {
      type VersionTypeOptions;
    }
    leaf MulticastRouterDetection {
      type RouterDetectionTypeOptions;
    }
    leaf EnableFastLeave {
      type boolean;
    }
    leaf EnableReportSuppression {
      type boolean;
    }
    leaf GroupLimit {
      type int32;
    }
    leaf GroupMembershipInterval {
      type int32;
    }
    leaf LastMemberQueryTime {
      type int32;
    }
    leaf MaxResponseTime {
      type int32;
    }
    leaf RouterAgingTime {
      type int32;
    }
    leaf StartQueryCount {
      type int32;
    }
    leaf StartQueryInterval {
      type int32;
    }
    leaf QueryInterval {
      type int32;
    }
    leaf Robustness {
      type int32;
    }
    container IdentifyiesConfig {
      list IdentifyiesConfig_Entry {
        uses PortEnabledEntry;
      }
    }
  }
  /* core/multicast/multicast.proto */
  grouping UnregisterFlood {
    container VlanList {
      list VlanList_Entry {
        uses UnregisterFloodVlan;
      }
    }
  }
  /* core/multicast/multicast.proto */
  grouping UnregisterFloodVlan {
    leaf VlanID {
      type int32;
    }
    leaf Enabled {
      type boolean;
    }
  }
  /* core/multicast/multicast.proto */
  grouping RouterPort {
    container VlanList {
      list VlanList_Entry {
        uses RouterPortVlanEntry;
      }
    }
  }
  /* core/multicast/multicast.proto */
  grouping RouterPortVlanEntry {
    leaf VlanID {
      type int32;
    }
    container PortList {
      list PortList_Entry {
        uses PortEnabledEntry;
      }
    }
  }
  /* core/multicast/multicast.proto */
  grouping PortEnabledEntry {
    container IdentifyNo {
      uses intri-device:InterfaceIdentify;
    }
    leaf Enabled {
      type boolean;
    }
  }
  /* core/multicast/multicast.proto */
  grouping Static {
    container List {
      list List_Entry {
        uses StaticGroupsConfigEntry;
      }
    }
  }
  /* core/multicast/multicast.proto */
  grouping StaticGroupsConfigEntry {
    leaf VlanID {
      type int32;
    }
    leaf Name {
      type string;
    }
    leaf MulticastAddress {
      type string;
    }
    container ForwardingPort {
      uses intri-device:PortList;
    }
  }
  /* core/multicast/multicast.proto */
  grouping IGMPStatistics {
    container List {
      list List_Entry {
        uses IGMPStatisticEntry;
      }
    }
  }
  /* core/multicast/multicast.proto */
  grouping IGMPStatisticEntry {
    leaf VlanID {
      type int32;
    }
    leaf RxGeneralQueries {
      type int32;
    }
    leaf RxV3Reports {
      type int32;
    }
    leaf RxV2Reports {
      type int32;
    }
    leaf RxV2Leaves {
      type int32;
    }
    leaf RxV1Reports {
      type int32;
    }
    leaf Querier {
      type boolean;
    }
  }
  /* core/multicast/multicast.proto */
  grouping RouterStatus {
    container VlanList {
      list VlanList_Entry {
        uses RouterStatusEntry;
      }
    }
  }
  /* core/multicast/multicast.proto */
  grouping RouterStatusEntry {
    leaf VlanID {
      type int32;
    }
    container List {
      list List_Entry {
        uses RouterPortStatusEntry;
      }
    }
  }
  /* core/multicast/multicast.proto */
  grouping RouterPortStatusEntry {
    leaf Type {
      type ProtocolTypeOptions;
    }
    leaf Status {
      type RouterStatusTypeOptions;
    }
    container IdentifyNo {
      uses intri-device:InterfaceIdentify;
    }
  }
  /* core/multicast/multicast.proto */
  grouping DynamicGroups {
    container List {
      list List_Entry {
        uses DynamicGroupEntry;
      }
    }
  }
  /* core/multicast/multicast.proto */
  grouping DynamicGroupEntry {
    leaf VlanID {
      type int32;
    }
    leaf Address {
      type string;
    }
    leaf TTL {
      type int32;
    }
    container IdentifyList {
      list IdentifyList_Entry {
        uses intri-device:InterfaceIdentify;
      }
    }
  }
  /* core/multicast/multicast.proto */
  grouping MLDStatistics {
    container List {
      list List_Entry {
        uses MLDStatisticEntry;
      }
    }
  }
  /* core/multicast/multicast.proto */
  grouping MLDStatisticEntry {
    leaf VlanID {
      type int32;
    }
    leaf RxGeneralQueries {
      type int32;
    }
    leaf RxV2Reports {
      type int32;
    }
    leaf RxV1Reports {
      type int32;
    }
    leaf RxV1Leaves {
      type int32;
    }
    leaf Querier {
      type boolean;
    }
  }
  /* core/multicast/multicast.proto */
  grouping VlanList {
    container List {
      leaf-list List_Entry {
        type int32;
      }
    }
  }


  /* **************************************************************************************************
   * Services    : 1                                                                                  *
   ************************************************************************************************** */

  /* **************************************************************************************************
   * Service     : Multicast                                                                          *
   * Methods     : 20                                                                                 *
   ************************************************************************************************** */
  /* core/multicast/service.proto */
  rpc intri-multicast-GetConfig {
    output  {
      uses Config;
    }
  }
  /* core/multicast/service.proto */
  rpc intri-multicast-SetIGMPSnoopingEnabled {
    input  {
      uses intri-common:Enabled;
    }
  }
  /* core/multicast/service.proto */
  rpc intri-multicast-SetMLDSnoopingEnabled {
    input  {
      uses intri-common:Enabled;
    }
  }
  /* core/multicast/service.proto */
  rpc intri-multicast-GetIGMPSnoopingConfig {
    input  {
      uses VlanList;
    }
    output  {
      uses Snooping;
    }
  }
  /* core/multicast/service.proto */
  rpc intri-multicast-SetIGMPSnoopingConfig {
    input  {
      uses Snooping;
    }
  }
  /* core/multicast/service.proto */
  rpc intri-multicast-GetMLDSnoopingConfig {
    input  {
      uses VlanList;
    }
    output  {
      uses Snooping;
    }
  }
  /* core/multicast/service.proto */
  rpc intri-multicast-SetMLDSnoopingConfig {
    input  {
      uses Snooping;
    }
  }
  /* core/multicast/service.proto */
  rpc intri-multicast-GetStaticGroupConfig {
    input  {
      uses VlanList;
    }
    output  {
      uses Static;
    }
  }
  /* core/multicast/service.proto */
  rpc intri-multicast-UpdateStaticGroupConfig {
    input  {
      uses Static;
    }
  }
  /* core/multicast/service.proto */
  rpc intri-multicast-AddStaticGroupConfig {
    input  {
      uses Static;
    }
  }
  /* core/multicast/service.proto */
  rpc intri-multicast-DeleteStaticGroupConfig {
    input  {
      uses Static;
    }
  }
  /* core/multicast/service.proto */
  rpc intri-multicast-GetUnregisterFloodingConfig {
    input  {
      uses VlanList;
    }
    output  {
      uses UnregisterFlood;
    }
  }
  /* core/multicast/service.proto */
  rpc intri-multicast-SetUnregisterFloodingConfig {
    input  {
      uses UnregisterFlood;
    }
  }
  /* core/multicast/service.proto */
  rpc intri-multicast-GetRouterPortStatus {
    input  {
      uses VlanList;
    }
    output  {
      uses RouterStatus;
    }
  }
  /* core/multicast/service.proto */
  rpc intri-multicast-SetRouterPortConfig {
    input  {
      uses RouterPort;
    }
  }
  /* core/multicast/service.proto */
  rpc intri-multicast-GetRouterPortConfig {
    input  {
      uses VlanList;
    }
    output  {
      uses RouterPort;
    }
  }
  /* core/multicast/service.proto */
  rpc intri-multicast-GetIGMPGroups {
    input  {
      uses VlanList;
    }
    output  {
      uses DynamicGroups;
    }
  }
  /* core/multicast/service.proto */
  rpc intri-multicast-GetMLDGroups {
    input  {
      uses VlanList;
    }
    output  {
      uses DynamicGroups;
    }
  }
  /* core/multicast/service.proto */
  rpc intri-multicast-GetIGMPStatistics {
    input  {
      uses VlanList;
    }
    output  {
      uses IGMPStatistics;
    }
  }
  /* core/multicast/service.proto */
  rpc intri-multicast-GetMLDStatistics {
    input  {
      uses VlanList;
    }
    output  {
      uses MLDStatistics;
    }
  }

}
