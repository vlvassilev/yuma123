module sercom-timeofday {

  namespace "sercom:sercom-timeofday";
  prefix "sercom-timeofday";
  organization "
    Sercomm Inc.";
  contact "
    sercomm@sercomm.com.tw";
  revision 2022-06-24 {
    description "Build date.";
  }

  grouping TimeOfDay {
    leaf Hours {
      mandatory "true";
      type int32;
    }
    leaf Minutes {
      mandatory "true";
      type int32;
    }
    leaf Seconds {
      mandatory "true";
      type int32;
    }
    leaf Nanos {
      mandatory "true";
      type int32;
    }
  }
}
