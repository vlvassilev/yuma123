// Code generated by protoc-gen-yang. DO NOT EDIT.


/* ****************************************************************************************************
 * Import Path : "github.com/Intrising/intri-type/core/poe"                                           *
 * Dir Path    : github.com/Intrising/intri-type/core/poe                                             *
 * Go Package  : poe                                                                                  *
 * Files       : 3                                                                                    *
 **************************************************************************************************** */
module intri-poe {

  namespace "intri:intri-poe";

  prefix "intri-poe";

  organization "Intrising Inc.";

  contact "intrising@intrising.com.tw";

  revision 2022-06-23 {
    description "Build date.";
  }

  import intri-device {
    prefix intri-device;
  }
  import intri-hardware {
    prefix intri-hardware;
  }
  import intri-empty {
    prefix intri-empty;
  }


  /* **************************************************************************************************
   * Enums       : 1                                                                                  *
   ************************************************************************************************** */
  /* core/poe/common.proto */
  typedef LLDPDeliverUsageTypeOptions {
    type enumeration {
      enum LLDP_L2_USAGE_TYPE_L1 {
        description "";
        value 0;
      }
      enum LLDP_L2_USAGE_TYPE_L1_AUTO {
        description "";
        value 1;
      }
      enum LLDP_L2_USAGE_TYPE_LLDP {
        description "";
        value 2;
      }
      enum LLDP_L2_USAGE_TYPE_LLDP_AUTO {
        description "";
        value 3;
      }
      enum LLDP_L2_USAGE_TYPE_CDP {
        description "";
        value 4;
      }
      enum LLDP_L2_USAGE_TYPE_CDP_AUTO {
        description "";
        value 5;
      }
    }
  }


  /* **************************************************************************************************
   * Msgs        : 8                                                                                  *
   ************************************************************************************************** */
  /* core/poe/poe.proto */
  grouping Config {
    container Budget {
      uses SystemBudget;
    }
    container Port {
      uses PortConfig;
    }
  }
  /* core/poe/poe.proto */
  grouping SystemBudget {
    leaf MaxPowerAvailable {
      type int32;
    }
  }
  /* core/poe/poe.proto */
  grouping PortConfig {
    container List {
      list List_Entry {
        uses ConfigEntry;
      }
    }
  }
  /* core/poe/poe.proto */
  grouping ConfigEntry {
    container IdentifyNo {
      uses intri-device:InterfaceIdentify;
    }
    leaf Enabled {
      type boolean;
    }
    leaf Mode {
      type intri-hardware:PoEPortModeTypeOptions;
    }
    leaf Priority {
      type intri-hardware:PoEPriorityLevelTypeOptions;
    }
  }
  /* core/poe/poe.proto */
  grouping SystemStatus {
    leaf MinShutDownVoltage {
      type decimal64 {
        fraction-digits 2;
      }
    }
    leaf MaxShutDownVoltage {
      type decimal64 {
        fraction-digits 2;
      }
    }
    leaf VMainVoltage {
      type decimal64 {
        fraction-digits 2;
      }
    }
    leaf IMainCurrent {
      type decimal64 {
        fraction-digits 2;
      }
    }
    leaf PowerConsumption {
      type decimal64 {
        fraction-digits 2;
      }
    }
  }
  /* core/poe/poe.proto */
  grouping PortStatus {
    container List {
      list List_Entry {
        uses PortStatusEntry;
      }
    }
  }
  /* core/poe/poe.proto */
  grouping PortStatusEntry {
    container IdentifyNo {
      uses intri-device:InterfaceIdentify;
    }
    leaf Condition {
      type intri-hardware:PoEConditionTypeOptions;
    }
    leaf DeterminedClass {
      type intri-hardware:PoEDeterminedClassTypeOptions;
    }
    leaf Priority {
      type intri-hardware:PoEPriorityLevelTypeOptions;
    }
    leaf OutputCurrent {
      type decimal64 {
        fraction-digits 2;
      }
    }
    leaf OutputVoltage {
      type decimal64 {
        fraction-digits 2;
      }
    }
    leaf OutputPower {
      type decimal64 {
        fraction-digits 2;
      }
    }
    leaf SupportMaxPower {
      type decimal64 {
        fraction-digits 2;
      }
    }
  }
  /* core/poe/poe.proto */
  grouping SetPoEMaxPowerAvailableRequest {
    leaf MaxPowerAvailable {
      type int32;
    }
  }


  /* **************************************************************************************************
   * Services    : 1                                                                                  *
   ************************************************************************************************** */

  /* **************************************************************************************************
   * Service     : PoE                                                                                *
   * Methods     : 6                                                                                  *
   ************************************************************************************************** */
  /* core/poe/service.proto */
  rpc intri-poe-GetConfig {
    output  {
      uses Config;
    }
  }
  /* core/poe/service.proto */
  rpc intri-poe-UpdatePortConfig {
    input  {
      uses PortConfig;
    }
  }
  /* core/poe/service.proto */
  rpc intri-poe-RunRestartPoEPort {
    input  {
      uses intri-device:PortList;
    }
  }
  /* core/poe/service.proto */
  rpc intri-poe-SetPoEMaxPowerAvailable {
    input  {
      uses SystemBudget;
    }
  }
  /* core/poe/service.proto */
  rpc intri-poe-GetPortStatus {
    input  {
      uses intri-device:PortList;
    }
    output  {
      uses PortStatus;
    }
  }
  /* core/poe/service.proto */
  rpc intri-poe-GetSystemStatus {
    output  {
      uses SystemStatus;
    }
  }

}
