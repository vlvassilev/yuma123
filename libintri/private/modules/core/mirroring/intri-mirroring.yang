module intri-mirroring {
  namespace "intri:intri-mirroring";
  prefix "intri-mirroring";
  import mirroringpb {
    prefix "mirroringpb";
  }
  organization "Intrising Inc.";
  contact "xxx@intrising.com.tw";
  revision 2022-06-14 {
    description "Build date.";
  }
}
