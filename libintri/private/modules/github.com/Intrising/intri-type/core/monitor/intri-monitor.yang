// Code generated by protoc-gen-yang. DO NOT EDIT.


/* ****************************************************************************************************
 * Import Path : "github.com/Intrising/intri-type/core/monitor"                                       *
 * Dir Path    : github.com/Intrising/intri-type/core/monitor                                         *
 * Go Package  : monitor                                                                              *
 * Files       : 3                                                                                    *
 **************************************************************************************************** */
module intri-monitor {

  namespace "intri:intri-monitor";

  prefix "intri-monitor";

  organization "Intrising Inc.";

  contact "intrising@intrising.com.tw";

  revision 2022-06-23 {
    description "Build date.";
  }

  import intri-event {
    prefix intri-event;
  }
  import intri-device {
    prefix intri-device;
  }
  import intri-empty {
    prefix intri-empty;
  }


  /* **************************************************************************************************
   * Enums       : 7                                                                                  *
   ************************************************************************************************** */
  /* core/monitor/common.proto */
  typedef DeviceMonitorTypeOptions {
    type enumeration {
      enum DEVICE_MONITOR_TYPE_TEMPERATURE {
        description "[Temperature] cpu temperature";
        value 0;
      }
      enum DEVICE_MONITOR_TYPE_FAN_1 {
        description "[Fan 1] fan 1 rpm";
        value 1;
      }
      enum DEVICE_MONITOR_TYPE_FAN_2 {
        description "[Fan 2] fan 2 rpm";
        value 2;
      }
      enum DEVICE_MONITOR_TYPE_FAN_3 {
        description "[Fan 3] fan 3 rpm";
        value 3;
      }
      enum DEVICE_MONITOR_TYPE_POWER {
        description "[Power] general power voltage";
        value 10;
      }
      enum DEVICE_MONITOR_TYPE_POWER_REDUNDANT_1_TEMPERATURE {
        description "[Power Redundant 1 Temperature] power redundant 1 temperature";
        value 11;
      }
      enum DEVICE_MONITOR_TYPE_POWER_REDUNDANT_1_CURRENT {
        description "[Power Redundant 1 Current] power redundant 1 current";
        value 12;
      }
      enum DEVICE_MONITOR_TYPE_POWER_REDUNDANT_1_VOLTAGE {
        description "[Power Redundant 1 Voltage] power redundant 1 voltage";
        value 13;
      }
      enum DEVICE_MONITOR_TYPE_POWER_REDUNDANT_1_CONSUMPTION {
        description "[Power Redundant 1 Consumption] power redundant 1 consumption";
        value 14;
      }
      enum DEVICE_MONITOR_TYPE_POWER_REDUNDANT_2_TEMPERATURE {
        description "[Power Redundant 2 Temperature] power redundant 2 temperature";
        value 15;
      }
      enum DEVICE_MONITOR_TYPE_POWER_REDUNDANT_2_CURRENT {
        description "[Power Redundant 2 Current] power redundant 2 current";
        value 16;
      }
      enum DEVICE_MONITOR_TYPE_POWER_REDUNDANT_2_VOLTAGE {
        description "[Power Redundant 2 Voltage] power redundant 2 voltage";
        value 17;
      }
      enum DEVICE_MONITOR_TYPE_POWER_REDUNDANT_2_CONSUMPTION {
        description "[Power Redundant 2 Consumption] power redundant 2 consumption";
        value 18;
      }
    }
  }
  /* core/monitor/common.proto */
  typedef SystemMonitorTypeOptions {
    type enumeration {
      enum SYSTEM_MONITOR_TYPE_CPU_UTILIZATION {
        description "[CPU] CPU utilization.";
        value 0;
      }
      enum SYSTEM_MONITOR_TYPE_MEMORY_UTILIZATION {
        description "[Memory] Memory utilization.";
        value 1;
      }
    }
  }
  /* core/monitor/common.proto */
  typedef ValueTypeOptions {
    type enumeration {
      enum VALUE_TYPE_INT {
        description "[Int] the value is an int32.";
        value 0;
      }
      enum VALUE_TYPE_FLOAT {
        description "[float] the value is a float32.";
        value 1;
      }
      enum VALUE_TYPE_INT64 {
        description "[Int64] the value is an int64.";
        value 2;
      }
      enum VALUE_TYPE_FLOAT64 {
        description "[float64] the value is an float64.";
        value 3;
      }
    }
  }
  /* core/monitor/common.proto */
  typedef LimitBoundaryTypeOptions {
    type enumeration {
      enum LIMIT_BOUNDARY_TYPE_NONE {
        description "[None] Has not supported the boundary settings.";
        value 0;
      }
      enum LIMIT_BOUNDARY_TYPE_INCLUDE {
        description "[Include] When the value includes the boundary will send an event.";
        value 1;
      }
      enum LIMIT_BOUNDARY_TYPE_EXCLUDE {
        description "[Exclude] When the value excludes the boundary will send an event.";
        value 2;
      }
    }
  }
  /* core/monitor/common.proto */
  typedef HardwareLEDTypeOptions {
    type enumeration {
      enum HARDWARE_LED_TYPE_POWER {
        description "[Power]";
        value 0;
      }
      enum HARDWARE_LED_TYPE_SYSTEM {
        description "[System]";
        value 1;
      }
      enum HARDWARE_LED_TYPE_POE_MAX {
        description "[PoeMax]";
        value 2;
      }
      enum HARDWARE_LED_TYPE_FAN {
        description "[Fan]";
        value 3;
      }
      enum HARDWARE_LED_TYPE_GPS {
        description "[Gps]";
        value 4;
      }
    }
  }
  /* core/monitor/common.proto */
  typedef LEDColorTypeOptions {
    type enumeration {
      enum LED_COLOR_TYPE_GREEN {
        description "[Green] The LED color is green.";
        value 0;
      }
      enum LED_COLOR_TYPE_RED {
        description "[Red] The LED and color is red.";
        value 1;
      }
      enum LED_COLOR_TYPE_ORANGE {
        description "[Orange] The LED and color is orange.";
        value 2;
      }
    }
  }
  /* core/monitor/common.proto */
  typedef LEDStateTypeOptions {
    type enumeration {
      enum LED_STATE_TYPE_OFF {
        description "[Off] The LED is disabled.";
        value 0;
      }
      enum LED_STATE_TYPE_ON {
        description "[On] The LED is enabled.";
        value 1;
      }
      enum LED_STATE_TYPE_BLINKING {
        description "[Blinking] The LED is blinking.";
        value 2;
      }
    }
  }


  /* **************************************************************************************************
   * Msgs        : 20                                                                                 *
   ************************************************************************************************** */
  /* core/monitor/monitor.proto */
  grouping Config {
    container DeviceLimitConfig {
      uses DeviceLimitConfig;
    }
    container SystemLimitConfig {
      uses SystemLimitConfig;
    }
  }
  /* core/monitor/monitor.proto */
  grouping DeviceLimitConfigEntry {
    leaf MonitorOption {
      type DeviceMonitorTypeOptions;
    }
    leaf LimitOption {
      type LimitBoundaryTypeOptions;
    }
    container Boundary {
      uses RangeValue;
    }
    leaf ValueOption {
      type ValueTypeOptions;
    }
    container Value {
      uses RangeValue;
    }
  }
  /* core/monitor/monitor.proto */
  grouping DeviceLimitConfig {
    container List {
      list List_Entry {
        uses DeviceLimitConfigEntry;
      }
    }
  }
  /* core/monitor/monitor.proto */
  grouping SystemLimitConfigEntry {
    leaf MonitorOption {
      type SystemMonitorTypeOptions;
    }
    leaf LimitOption {
      type LimitBoundaryTypeOptions;
    }
    container Boundary {
      uses RangeValue;
    }
    leaf ValueOption {
      type ValueTypeOptions;
    }
    container Value {
      uses RangeValue;
    }
  }
  /* core/monitor/monitor.proto */
  grouping SystemLimitConfig {
    container List {
      list List_Entry {
        uses SystemLimitConfigEntry;
      }
    }
  }
  /* core/monitor/monitor.proto */
  grouping RangeValue {
    leaf IntMin {
      type int32;
    }
    leaf IntMax {
      type int32;
    }
    leaf FloatMin {
      type decimal64 {
        fraction-digits 2;
      }
    }
    leaf FloatMax {
      type decimal64 {
        fraction-digits 2;
      }
    }
    leaf Int64Min {
      type int64;
    }
    leaf Int64Max {
      type int64;
    }
    leaf Float64Min {
      type decimal64 {
        fraction-digits 2;
      }
    }
    leaf Float64Max {
      type decimal64 {
        fraction-digits 2;
      }
    }
  }
  /* core/monitor/monitor.proto */
  grouping DeviceScorllBarValueEntry {
    leaf MonitorOption {
      type DeviceMonitorTypeOptions;
    }
    container Value {
      uses RangeValue;
    }
  }
  /* core/monitor/monitor.proto */
  grouping DeviceScorllBarValue {
    container List {
      list List_Entry {
        uses DeviceScorllBarValueEntry;
      }
    }
  }
  /* core/monitor/monitor.proto */
  grouping SystemScorllBarValueEntry {
    leaf MonitorOption {
      type SystemMonitorTypeOptions;
    }
    container Value {
      uses RangeValue;
    }
  }
  /* core/monitor/monitor.proto */
  grouping SystemScorllBarValue {
    container List {
      list List_Entry {
        uses SystemScorllBarValueEntry;
      }
    }
  }
  /* core/monitor/monitor.proto */
  grouping Status {
    container DeviceStatus {
      uses DeviceStatus;
    }
    container SystemStatus {
      uses SystemStatus;
    }
    container LedStatus {
      uses LEDStatus;
    }
  }
  /* core/monitor/monitor.proto */
  grouping DeviceStatusEntry {
    leaf MonitorOption {
      type DeviceMonitorTypeOptions;
    }
    container Value {
      uses DisplayValue;
    }
    leaf LoggingOption {
      type intri-event:LoggingTypeOptions;
    }
  }
  /* core/monitor/monitor.proto */
  grouping DeviceStatus {
    container List {
      list List_Entry {
        uses DeviceStatusEntry;
      }
    }
  }
  /* core/monitor/monitor.proto */
  grouping SystemStatusEntry {
    leaf MonitorOption {
      type SystemMonitorTypeOptions;
    }
    container Value {
      uses DisplayValue;
    }
    leaf LoggingOption {
      type intri-event:LoggingTypeOptions;
    }
  }
  /* core/monitor/monitor.proto */
  grouping SystemStatus {
    container List {
      list List_Entry {
        uses SystemStatusEntry;
      }
    }
  }
  /* core/monitor/monitor.proto */
  grouping DisplayValue {
    leaf ValueUnit {
      type string;
    }
    leaf IntValue {
      type int32;
    }
    leaf FloatValue {
      type decimal64 {
        fraction-digits 2;
      }
    }
    leaf Int64Value {
      type int64;
    }
    leaf Float64Value {
      type decimal64 {
        fraction-digits 2;
      }
    }
  }
  /* core/monitor/monitor.proto */
  grouping LEDStatus {
    container SystemList {
      list SystemList_Entry {
        uses SystemLEDStatusEntry;
      }
    }
    container PortList {
      list PortList_Entry {
        uses PortLEDStatusEntry;
      }
    }
  }
  /* core/monitor/monitor.proto */
  grouping SystemLEDStatusEntry {
    leaf LedType {
      type HardwareLEDTypeOptions;
    }
    container LedState {
      uses LEDStateEntry;
    }
  }
  /* core/monitor/monitor.proto */
  grouping PortLEDStatusEntry {
    container IdentifyNo {
      uses intri-device:InterfaceIdentify;
    }
    leaf IsSfp {
      type boolean;
    }
    container LinkLedState {
      uses LEDStateEntry;
    }
    leaf IsSupportPoELed {
      type boolean;
    }
    container PoELedState {
      uses LEDStateEntry;
    }
    leaf IsSupportSpeedLed {
      type boolean;
    }
    container SpeedLedState {
      uses LEDStateEntry;
    }
  }
  /* core/monitor/monitor.proto */
  grouping LEDStateEntry {
    leaf StateOption {
      type LEDStateTypeOptions;
    }
    leaf ColorOption {
      type LEDColorTypeOptions;
    }
    leaf BlinkingIntervalMs {
      type int32;
    }
  }


  /* **************************************************************************************************
   * Services    : 1                                                                                  *
   ************************************************************************************************** */

  /* **************************************************************************************************
   * Service     : Monitor                                                                            *
   * Methods     : 11                                                                                 *
   ************************************************************************************************** */
  /* core/monitor/service.proto */
  rpc intri-monitor-GetConfig {
    output  {
      uses Config;
    }
  }
  /* core/monitor/service.proto */
  rpc intri-monitor-GetDeviceLimitConfig {
    output  {
      uses DeviceLimitConfig;
    }
  }
  /* core/monitor/service.proto */
  rpc intri-monitor-UpdateDeviceScorllBarValueEntry {
    input  {
      uses DeviceScorllBarValueEntry;
    }
  }
  /* core/monitor/service.proto */
  rpc intri-monitor-UpdateDeviceScorllBarValue {
    input  {
      uses DeviceScorllBarValue;
    }
  }
  /* core/monitor/service.proto */
  rpc intri-monitor-GetSystemLimitConfig {
    output  {
      uses SystemLimitConfig;
    }
  }
  /* core/monitor/service.proto */
  rpc intri-monitor-UpdateSystemScorllBarValueEntry {
    input  {
      uses SystemScorllBarValueEntry;
    }
  }
  /* core/monitor/service.proto */
  rpc intri-monitor-UpdateSystemScorllBarValue {
    input  {
      uses SystemScorllBarValue;
    }
  }
  /* core/monitor/service.proto */
  rpc intri-monitor-GetStatus {
    output  {
      uses Status;
    }
  }
  /* core/monitor/service.proto */
  rpc intri-monitor-GetDeviceStatus {
    output  {
      uses DeviceStatus;
    }
  }
  /* core/monitor/service.proto */
  rpc intri-monitor-GetSystemStatus {
    output  {
      uses SystemStatus;
    }
  }
  /* core/monitor/service.proto */
  rpc intri-monitor-GetLEDStatus {
    output  {
      uses LEDStatus;
    }
  }

}
