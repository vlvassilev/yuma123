submodule intri-isolation-msg {
  belongs-to "intri-isolation" {
    prefix "intri-isolation-msg";
  }
  include intri-isolation-enum;
  import devicepb {
    prefix "devicepb";
  }
  import isolationpb {
    prefix "isolationpb";
  }
  revision 2022-06-14 {
    description "Build date.";
  }
  // core/isolation/isolation.proto
  grouping ConfigEntry {
    container ConfigEntry_IdentifyNo {
      uses devicepb:InterfaceIdentify;
    }
    container ConfigEntry_AllowOutgoingList {
      uses devicepb:InterfaceIdentify;
    }
  }
  // core/isolation/isolation.proto
  grouping Config {
    container Config_List {
      uses isolationpb:ConfigEntry;
    }
  }
}
