module b {
    yang-version 1.1;

    namespace "http://example.com/ns/identityref-typedef-b";

    prefix "b";

    import a {
      prefix a;
    }

    organization  "example.com";

    description 
      "Testing identityref typedef type defined in imported module.";

    revision 2018-08-06 {
        description
            "Corrected example to actually define identities
             based on twa baseless (abstract) identities.";
    }
    container b {
        leaf my-identityref-typedef-type-leaf {
            type a:my-identityref-typedef-type;
        }
    }
}
