// Code generated by protoc-gen-yang. DO NOT EDIT.


/* ****************************************************************************************************
 * Import Path : "github.com/Intrising/intri-type/cpss"                                               *
 * Dir Path    : github.com/Intrising/intri-type/cpss                                                 *
 * Go Package  : cpss                                                                                 *
 * Files       : 17                                                                                   *
 **************************************************************************************************** */
module intri-cpss {

  namespace "intri:intri-cpss";

  prefix "intri-cpss";

  organization "Intrising Inc.";

  contact "intrising@intrising.com.tw";

  revision 2022-06-23 {
    description "Build date.";
  }

  import intri-empty {
    prefix intri-empty;
  }


  /* **************************************************************************************************
   * Enums       : 29                                                                                 *
   ************************************************************************************************** */
  /* cpss/common.proto */
  typedef ActionTypeOptions {
    type enumeration {
      enum ACTION_TYPE_ADD {
        description "[Add] Action type add";
        value 0;
      }
      enum ACTION_TYPE_DELETE {
        description "[Delete] Action type delete";
        value 1;
      }
      enum ACTION_TYPE_UPDATE {
        description "[Update] Action type update";
        value 2;
      }
      enum ACTION_TYPE_GET {
        description "[Get] Action type get";
        value 3;
      }
    }
  }
  /* cpss/common.proto */
  typedef InterfaceTypeOptions {
    type enumeration {
      enum INTERFACE_TYPE_VLAN {
        description "[Vlan] Interface type vlan";
        value 0;
      }
      enum INTERFACE_TYPE_PORT {
        description "[Port] Interface type port";
        value 1;
      }
      enum INTERFACE_TYPE_TRUNK {
        description "[Trunk] Interface type trunk";
        value 2;
      }
      enum INTERFACE_TYPE_VIDX {
        description "[Vidx] Interface type vidx";
        value 3;
      }
      enum INTERFACE_TYPE_MULTICAST {
        description "[Multicast] Interface type multicast";
        value 4;
      }
      enum INTERFACE_TYPE_VLAN_PORT {
        description "[Vlan Port] Interface type vlan port";
        value 5;
      }
      enum INTERFACE_TYPE_VLAN_TRUNK {
        description "[Vlan Trunk] Interface type vlan trunk";
        value 6;
      }
      enum INTERFACE_TYPE_PORT_TRUNK {
        description "[Port Trunk] Interface type port trunk";
        value 7;
      }
      enum INTERFACE_TYPE_ANY {
        description "[Any] Interface type any";
        value 8;
      }
    }
  }
  /* cpss/common.proto */
  typedef PacketCommandOptions {
    type enumeration {
      enum PACKET_COMMAND_FORWARD {
        description "";
        value 0;
      }
      enum PACKET_COMMAND_MIRROR {
        description "";
        value 1;
      }
      enum PACKET_COMMAND_TRAP {
        description "";
        value 2;
      }
      enum PACKET_COMMAND_DROP {
        description "";
        value 3;
      }
    }
  }
  /* cpss/common.proto */
  typedef PortSpeedDuplexOptions {
    type enumeration {
      enum PORT_SPEED_DUPLEX_AUTO {
        description "";
        value 0;
      }
      enum PORT_SPEED_DUPLEX_10M_FULL {
        description "";
        value 1;
      }
      enum PORT_SPEED_DUPLEX_100M_FULL {
        description "";
        value 3;
      }
      enum PORT_SPEED_DUPLEX_1000M_FULL {
        description "";
        value 5;
      }
      enum PORT_SPEED_DUPLEX_2500M_FULL {
        description "";
        value 6;
      }
      enum PORT_SPEED_DUPLEX_5G_FULL {
        description "";
        value 7;
      }
      enum PORT_SPEED_DUPLEX_10G_FULL {
        description "";
        value 8;
      }
      enum PORT_SPEED_DUPLEX_25G_FULL {
        description "";
        value 9;
      }
      enum PORT_SPEED_DUPLEX_40G_FULL {
        description "";
        value 10;
      }
      enum PORT_SPEED_DUPLEX_100G_FULL {
        description "";
        value 11;
      }
    }
  }
  /* cpss/common.proto */
  typedef PortTypeOptions {
    type enumeration {
      enum PORT_TYPE_10M_FULL {
        description "[10 M Full] Port type 10 m full";
        value 0;
      }
      enum PORT_TYPE_100M_FULL {
        description "[100 M Full] Port type 100 m full";
        value 2;
      }
      enum PORT_TYPE_1000M_FULL {
        description "[1000 M Full] Port type 1000 m full";
        value 4;
      }
      enum PORT_TYPE_2500M_FULL {
        description "[2500 M Full] Port type 2500 m full";
        value 5;
      }
      enum PORT_TYPE_5G_FULL {
        description "[5 G Full] Port type 5 g full";
        value 6;
      }
      enum PORT_TYPE_10G_FULL {
        description "[10 G Full] Port type 10 g full";
        value 7;
      }
      enum PORT_TYPE_25G_FULL {
        description "[25 G Full] Port type 25 g full";
        value 8;
      }
      enum PORT_TYPE_40G_FULL {
        description "[40 G Full] Port type 40 g full";
        value 9;
      }
      enum PORT_TYPE_100G_FULL {
        description "[100 G Full] Port type 100 g full";
        value 10;
      }
    }
  }
  /* cpss/common.proto */
  typedef PortMediaOptions {
    type enumeration {
      enum PORT_MEDIA_COPPER {
        description "";
        value 0;
      }
      enum PORT_MEDIA_RJ45 {
        description "";
        value 1;
      }
      enum PORT_MEDIA_SFP {
        description "";
        value 2;
      }
      enum PORT_MEDIA_STACKING {
        description "";
        value 3;
      }
      enum PORT_MEDIA_POE {
        description "";
        value 4;
      }
      enum PORT_MEDIA_POE_PLUS {
        description "";
        value 5;
      }
      enum PORT_MEDIA_POE_PLUS_PLUS {
        description "";
        value 6;
      }
      enum PORT_MEDIA_UP_LINK_PORT {
        description "";
        value 7;
      }
      enum PORT_MEDIA_DOWN_LINK_PORT {
        description "";
        value 8;
      }
    }
  }
  /* cpss/common.proto */
  typedef STPProtocolTypeOptions {
    type enumeration {
      enum STP_PROTOCOL_TYPE_CPSS {
        description "[Cpss] Stp protocol type cpss";
        value 0;
      }
      enum STP_PROTOCOL_TYPE_DHCP {
        description "[Dhcp] Stp protocol type dhcp";
        value 10;
      }
      enum STP_PROTOCOL_TYPE_STORM_CONTROL {
        description "[Dhcp] Stp protocol type storm control";
        value 20;
      }
      enum STP_PROTOCOL_TYPE_LOOP {
        description "[Loop] Stp protocol type loop";
        value 30;
      }
      enum STP_PROTOCOL_TYPE_PORT {
        description "[Core] Stp protocol type port";
        value 40;
      }
      enum STP_PROTOCOL_TYPE_LACP {
        description "[Lacp] Stp protocol type lacp";
        value 70;
      }
      enum STP_PROTOCOL_TYPE_PACC {
        description "[Stp] Stp protocol type PACC";
        value 80;
      }
      enum STP_PROTOCOL_TYPE_STP {
        description "[Stp] Stp protocol type stp";
        value 90;
      }
      enum STP_PROTOCOL_TYPE_G8032 {
        description "[G8032] Stp protocol type g8032";
        value 100;
      }
    }
  }
  /* cpss/common.proto */
  typedef STPPortStateTypeOptions {
    type enumeration {
      enum STP_PORT_STATE_TYPE_DISABLE {
        description "[Disable] Stp port state type disable";
        value 0;
      }
      enum STP_PORT_STATE_TYPE_BLOCKING {
        description "[Blocking] Stp port state type blocking";
        value 1;
      }
      enum STP_PORT_STATE_TYPE_LEARNING {
        description "[Learning] Stp port state type learning";
        value 2;
      }
      enum STP_PORT_STATE_TYPE_FORWARDING {
        description "[Forwarding] Stp port state type forwarding";
        value 3;
      }
    }
  }
  /* cpss/common.proto */
  typedef ACLDirectionTypeOptions {
    type enumeration {
      enum ACL_DIRECTION_TYPE_INGRESS {
        description "[Ingress] Acl direction type ingress";
        value 0;
      }
      enum ACL_DIRECTION_TYPE_EGRESS {
        description "[Egress] Acl direction type egress";
        value 1;
      }
    }
  }
  /* cpss/common.proto */
  typedef ACLRuleTypeOptions {
    type enumeration {
      enum ACL_RULE_TYPE_MAC {
        description "[Mac] Acl rule type mac";
        value 0;
      }
      enum ACL_RULE_TYPE_IPV4 {
        description "[Ipv4] Acl rule type ipv4";
        value 1;
      }
      enum ACL_RULE_TYPE_IPV6 {
        description "[Ipv6] Acl rule type ipv6";
        value 2;
      }
      enum ACL_RULE_TYPE_STP {
        description "[Stp] Acl rule type stp";
        value 3;
      }
      enum ACL_RULE_TYPE_LACP {
        description "[Lacp] Acl rule type lacp";
        value 4;
      }
      enum ACL_RULE_TYPE_DOT1X {
        description "[Dot1 X] Acl rule type dot1 x";
        value 5;
      }
      enum ACL_RULE_TYPE_ARP {
        description "[Arp] Acl rule type arp";
        value 6;
      }
      enum ACL_RULE_TYPE_DHCPV4_SRC_67_DST_68 {
        description "[Dhcpv4 Src 67 Dst 68] Acl rule type dhcpv4 src 67 dst 68";
        value 7;
      }
      enum ACL_RULE_TYPE_DHCPV4_SRC_68_DST_67 {
        description "[Dhcpv4 Src 68 Dst 67] Acl rule type dhcpv4 src 68 dst 67";
        value 8;
      }
      enum ACL_RULE_TYPE_LOOP {
        description "[Loop] Acl rule type loop";
        value 9;
      }
      enum ACL_RULE_TYPE_G8032 {
        description "[G8032] Acl rule type g8032";
        value 10;
      }
      enum ACL_RULE_TYPE_MAC_IP_BINDING {
        description "[Mac Ip Binding] Acl rule type mac ip binding";
        value 11;
      }
      enum ACL_RULE_TYPE_SUBNET_BASED {
        description "[Subnet Based] Acl rule type subnet based";
        value 12;
      }
      enum ACL_RULE_TYPE_MAC_BASED {
        description "[Mac Based] Acl rule type mac based";
        value 13;
      }
      enum ACL_RULE_TYPE_SELECTIVE_QINQ {
        description "[Selective Qinq] Acl rule type selective qinq";
        value 14;
      }
      enum ACL_RULE_TYPE_FLOW_MIRROR {
        description "[Flow Mirror] Acl rule type flow mirror";
        value 15;
      }
      enum ACL_RULE_TYPE_MAC_COUNTING {
        description "[Mac Counting] Acl rule type mac counting";
        value 16;
      }
      enum ACL_RULE_TYPE_PTP_MESSAGE {
        description "[PTP Message] Acl rule type ptp message";
        value 17;
      }
      enum ACL_RULE_TYPE_INCOMING_BLOCK {
        description "[Icoming Deny] Acl rule for deny the incoming packets";
        value 18;
      }
    }
  }
  /* cpss/common.proto */
  typedef CNCCountingTypeOptions {
    type enumeration {
      enum CNC_COUNTING_TYPE_MAC_COUNTING {
        description "[Mac Counting] Cnc counting type mac counting";
        value 0;
      }
    }
  }
  /* cpss/common.proto */
  typedef FDBLayerTypeOptions {
    type enumeration {
      enum FDB_LAYER_TYPE_2 {
        description "[Layer 2] FDB layer type 2";
        value 0;
      }
      enum FDB_LAYER_TYPE_3 {
        description "[Layer 3] FDB layer type 3";
        value 1;
      }
    }
  }
  /* cpss/common.proto */
  typedef FDBEntryActionTypeOptions {
    type enumeration {
      enum FDB_ENTRY_ACTION_TYPE_ADD {
        description "[Add] FDB entry action type add";
        value 0;
      }
      enum FDB_ENTRY_ACTION_TYPE_DELETE {
        description "[Delete] FDB entry action type delete";
        value 1;
      }
    }
  }
  /* cpss/common.proto */
  typedef MulticastEntryTypeOptions {
    type enumeration {
      enum MULTICAST_ENTRY_TYPE_MAC {
        description "[MAC] Multicast entry type mac";
        value 0;
      }
      enum MULTICAST_ENTRY_TYPE_IPV4 {
        description "[IPv4] Multicast entry type i pv4";
        value 1;
      }
      enum MULTICAST_ENTRY_TYPE_IPV6 {
        description "[IPv6] Multicast entry type i pv6";
        value 2;
      }
    }
  }
  /* cpss/common.proto */
  typedef VIDXEntryTypeOptions {
    type enumeration {
      enum VIDX_ENTRY_TYPE_VLAN_FLOODING {
        description "";
        value 0;
      }
      enum VIDX_ENTRY_TYPE_BRIDGE_MULTICAST {
        description "";
        value 1;
      }
    }
  }
  /* cpss/common.proto */
  typedef MirroringDirectionTypeOptions {
    type enumeration {
      enum MIRRORING_DIRECTION_TYPE_NONE {
        description "[None] Mirroring direction type none";
        value 0;
      }
      enum MIRRORING_DIRECTION_TYPE_TX_ONLY {
        description "[Tx Only] Mirroring direction type tx only";
        value 1;
      }
      enum MIRRORING_DIRECTION_TYPE_RX_ONLY {
        description "[Rx Only] Mirroring direction type rx only";
        value 2;
      }
      enum MIRRORING_DIRECTION_TYPE_BOTH {
        description "[Both] Mirroring direction type both";
        value 3;
      }
    }
  }
  /* cpss/common.proto */
  typedef QoSTrustModeOptions {
    type enumeration {
      enum QOS_TRUST_MODE_DISABLED {
        description "[Disabled] Qos trust mode disabled";
        value 0;
      }
      enum QOS_TRUST_MODE_COS {
        description "[CoS] Qos trust mode cos";
        value 1;
      }
      enum QOS_TRUST_MODE_DSCP_ONLY {
        description "[DSCP Only] Qos trust mode dscp only";
        value 2;
      }
      enum QOS_TRUST_MODE_DSCP_FIRST {
        description "[DSCP First] Qos trust mode dscp first";
        value 3;
      }
    }
  }
  /* cpss/common.proto */
  typedef QoSSchedulerTypeOptions {
    type enumeration {
      enum QOS_SCHEDULER_TYPE_WEIGHTED {
        description "[Weighted] Qos scheduler type weighted";
        value 0;
      }
      enum QOS_SCHEDULER_TYPE_STRICT {
        description "[Strict] Qos scheduler type strict";
        value 1;
      }
    }
  }
  /* cpss/common.proto */
  typedef RateLimitingIngressFilterTypeOptions {
    type enumeration {
      enum RATE_LIMITING_INGRESS_FILTER_TYPE_UC_KNOWN {
        description "[UC Known] Rate limiting ingress filter type uc known";
        value 0;
      }
      enum RATE_LIMITING_INGRESS_FILTER_TYPE_UC_UNKNOWN {
        description "[UC Unknown] Rate limiting ingress filter type uc unknown";
        value 1;
      }
      enum RATE_LIMITING_INGRESS_FILTER_TYPE_MC_UNREGISTERED {
        description "[MC Unregistered] Rate limiting ingress filter type mc unregistered";
        value 2;
      }
      enum RATE_LIMITING_INGRESS_FILTER_TYPE_MC_REGISTERED {
        description "[MC Registered] Rate limiting ingress filter type mc registered";
        value 3;
      }
      enum RATE_LIMITING_INGRESS_FILTER_TYPE_BC {
        description "[BC] Rate limiting ingress filter type bc";
        value 4;
      }
    }
  }
  /* cpss/common.proto */
  typedef TrunkingLoadBalanceModeOptions {
    type enumeration {
      enum TRUNKING_LOAD_BALANCE_MODE_SRC_DST_MAC {
        description "[Source/Destination MAC] Trunking load balance mode src dst mac";
        value 0;
      }
      enum TRUNKING_LOAD_BALANCE_MODE_SRC_DST_IP {
        description "[Source/Destination IP] Trunking load balance mode src dst ip";
        value 1;
      }
      enum TRUNKING_LOAD_BALANCE_MODE_SRC_DST_MAC_IP {
        description "[Source/Destination MAC and IP] Trunking load balance mode src dst mac ip";
        value 2;
      }
    }
  }
  /* cpss/common.proto */
  typedef VlanTaggingCommandTypeOptions {
    type enumeration {
      enum VLAN_TAGGING_COMMAND_TYPE_UNTAGGED {
        description "[Untagged] Vlan tagging command type untagged";
        value 0;
      }
      enum VLAN_TAGGING_COMMAND_TYPE_TAGGED {
        description "[Tagged] Vlan tagging command type tagged";
        value 1;
      }
      enum VLAN_TAGGING_COMMAND_TYPE_QINQ_PROVIDER {
        description "[QinQ Provider] Vlan tagging command type qinq provider";
        value 2;
      }
      enum VLAN_TAGGING_COMMAND_TYPE_QINQ_CUSTOMER {
        description "[QinQ Customer] Vlan tagging command type qinq customer";
        value 3;
      }
    }
  }
  /* cpss/common.proto */
  typedef VlanAcceptFrameTypeOptions {
    type enumeration {
      enum VLAN_ACCEPT_FRAME_TYPE_ALL {
        description "[All] Vlan accept frame type all";
        value 0;
      }
      enum VLAN_ACCEPT_FRAME_TYPE_UNTAGGED_ONLY {
        description "[Untagged Only] Vlan accept frame type untagged only";
        value 1;
      }
      enum VLAN_ACCEPT_FRAME_TYPE_TAGGED_ONLY {
        description "[Tagged Only] Vlan accept frame type tagged only";
        value 2;
      }
    }
  }
  /* cpss/common.proto */
  typedef VlanTranslationMappingTypeOptions {
    type enumeration {
      enum VLAN_TRANSLATION_MAPPING_TYPE_ONE_TO_ONE {
        description "[One To One] Vlan translation mapping type one to one";
        value 0;
      }
      enum VLAN_TRANSLATION_MAPPING_TYPE_MANY_TO_ONE {
        description "[Many To One] Vlan translation mapping type many to one";
        value 1;
      }
    }
  }
  /* cpss/common.proto */
  typedef VlanProtocolBasedEncapsulationTypeOptions {
    type enumeration {
      enum VLAN_PROTOCOL_BASED_ENCAPSULATION_ETHERNET_V2 {
        description "[Ethernet V2] Vlan protocol based encapsulation ethernet v2";
        value 0;
      }
      enum VLAN_PROTOCOL_BASED_ENCAPSULATION_NON_LLC_SNAP {
        description "[None LLC Snap] Vlan protocol based encapsulation non llc snap";
        value 1;
      }
      enum VLAN_PROTOCOL_BASED_ENCAPSULATION_LLC_SNAP {
        description "[LLC Snap] Vlan protocol based encapsulation llc snap";
        value 2;
      }
    }
  }
  /* cpss/common.proto */
  typedef PacketControlProtocolTypeOptions {
    type enumeration {
      enum PACKET_CONTROL_PROTOCOL_TYPE_STP {
        description "[STP] Packet control protocol type stp";
        value 0;
      }
      enum PACKET_CONTROL_PROTOCOL_TYPE_LACP {
        description "[LACP] Packet control protocol type lacp";
        value 1;
      }
      enum PACKET_CONTROL_PROTOCOL_TYPE_DOT1X {
        description "[Dot1X] Packet control protocol type dot1 x";
        value 2;
      }
      enum PACKET_CONTROL_PROTOCOL_TYPE_LOOP {
        description "[Loop] Packet control protocol type loop";
        value 3;
      }
      enum PACKET_CONTROL_PROTOCOL_TYPE_DLDP {
        description "[DLDP] Packet control protocol type dldp";
        value 4;
      }
      enum PACKET_CONTROL_PROTOCOL_TYPE_DHCPV4_DISCOVER {
        description "[DHCP V4 Discover] Packet control protocol type dhcpv4 discover";
        value 5;
      }
      enum PACKET_CONTROL_PROTOCOL_TYPE_DHCPV4_BROADCAST_OFFER {
        description "[DHCP V4 Broadcast Offer] Packet control protocol type dhcpv4 broadcast offer";
        value 6;
      }
      enum PACKET_CONTROL_PROTOCOL_TYPE_DHCPV4_UDP_DST_67 {
        description "[DHCP V4 UDP Destination 67] Packet control protocol type dhcpv4 udp dst 67";
        value 7;
      }
      enum PACKET_CONTROL_PROTOCOL_TYPE_DHCPV4_UDP_DST_68 {
        description "[DHCP V4 UDP Destination 68] Packet control protocol type dhcpv4 udp dst 68";
        value 8;
      }
      enum PACKET_CONTROL_PROTOCOL_TYPE_ARP {
        description "[ARP] Packet control protocol type arp";
        value 9;
      }
      enum PACKET_CONTROL_PROTOCOL_TYPE_GVRP {
        description "[GVRP] Packet control protocol type gvrp";
        value 10;
      }
      enum PACKET_CONTROL_PROTOCOL_TYPE_IGMP {
        description "[IGMP] Packet control protocol type igmp";
        value 11;
      }
      enum PACKET_CONTROL_PROTOCOL_TYPE_MLD {
        description "[MLD] Packet control protocol type mld";
        value 12;
      }
    }
  }
  /* cpss/common.proto */
  typedef PHYInterfaceTypeOptions {
    type enumeration {
      enum PHY_INTERFACE_TYPE_SMI {
        description "[SMI] Phy interface type smi";
        value 0;
      }
      enum PHY_INTERFACE_TYPE_XSMI {
        description "[XSMI] Phy interface type xsmi";
        value 1;
      }
      enum PHY_INTERFACE_TYPE_UNUSED {
        description "[Unused] Phy interface type unused";
        value 2;
      }
    }
  }
  /* cpss/common.proto */
  typedef PTPSyncERecoveryClockSelectTypeOptions {
    type enumeration {
      enum PTP_SYNC_E_RECOVERY_CLOCK_SELECT_TYPE_0 {
        description "[Select Type 0] PTP sync e recovery clock select type 0";
        value 0;
      }
      enum PTP_SYNC_E_RECOVERY_CLOCK_SELECT_TYPE_1 {
        description "[Select Type 1] PTP sync e recovery clock select type 1";
        value 1;
      }
    }
  }
  /* cpss/ptp.proto */
  typedef PTPPortDelayTypeOptions {
    type enumeration {
      enum PTP_PORT_DELAY_INGRESS {
        description "";
        value 0;
      }
      enum PTP_PORT_DELAY_EGRESS {
        description "";
        value 1;
      }
    }
  }
  /* cpss/ptp.proto */
  typedef PTPModeTypeOptions {
    type enumeration {
      enum PTP_MODE_DISABLE {
        description "";
        value 0;
      }
      enum PTP_MODE_E2E_TC {
        description "";
        value 1;
      }
      enum PTP_MODE_P2P_TC {
        description "";
        value 2;
      }
      enum PTP_MODE_MASTER_BC {
        description "";
        value 3;
      }
      enum PTP_MODE_SLAVE_BC {
        description "";
        value 4;
      }
      enum PTP_MODE_GPTP_MASTER {
        description "";
        value 5;
      }
      enum PTP_MODE_GPTP_SLAVE {
        description "";
        value 6;
      }
      enum PTP_MODE_PASSIVE {
        description "";
        value 7;
      }
      enum PTP_MODE_LISTENING {
        description "";
        value 8;
      }
    }
  }


  /* **************************************************************************************************
   * Msgs        : 125                                                                                *
   ************************************************************************************************** */
  /* cpss/common.proto */
  grouping Enabled {
    leaf IsEnabled {
      type boolean;
    }
  }
  /* cpss/common.proto */
  grouping IndexList {
    container List {
      leaf-list List_Entry {
        type int32;
      }
    }
  }
  /* cpss/common.proto */
  grouping MACAddress {
    leaf Value {
      type string;
    }
  }
  /* cpss/device.proto */
  grouping DeviceArchitecture {
    container Information {
      uses DeviceInformation;
    }
    container PortAllocationTable {
      uses DevicePortAllocationTable;
    }
  }
  /* cpss/device.proto */
  grouping DeviceInformation {
    leaf Model {
      type string;
    }
    leaf MACAddress {
      type string;
    }
    leaf Description {
      type string;
    }
    leaf EnterpriseOID {
      type string;
    }
    leaf Vendor {
      type string;
    }
    leaf HardwareVersion {
      type string;
    }
    leaf SoftwareVersion {
      type string;
    }
  }
  /* cpss/device.proto */
  grouping DevicePortProperty {
    leaf PortNo {
      type int32;
    }
    leaf Type {
      type PortTypeOptions;
    }
    leaf MACNo {
      type int32;
    }
    container PHYInterface {
      uses PHYInterface;
    }
    leaf PHYID1 {
      type int32;
    }
    leaf PHYID2 {
      type int32;
    }
    leaf PHYChipID {
      type int32;
    }
    leaf PoENo {
      type int32;
    }
    leaf PoEChipNo {
      type int32;
    }
    leaf PoELEDNo {
      type int32;
    }
    container SupportedTypeList {
      leaf-list SupportedTypeList_Entry {
        type PortTypeOptions;
      }
    }
    container SupportedMediaList {
      leaf-list SupportedMediaList_Entry {
        type PortMediaOptions;
      }
    }
  }
  /* cpss/device.proto */
  grouping PHYInterface {
    leaf Interface {
      type int32;
    }
    leaf Type {
      type PHYInterfaceTypeOptions;
    }
  }
  /* cpss/device.proto */
  grouping DevicePortAllocationTable {
    leaf CPUPortNo {
      type int32;
    }
    container PortPropertyList {
      list PortPropertyList_Entry {
        uses DevicePortProperty;
      }
    }
    container PortList {
      leaf-list PortList_Entry {
        type int32;
      }
    }
    container MACNoList {
      leaf-list MACNoList_Entry {
        type int32;
      }
    }
    container PoEList {
      leaf-list PoEList_Entry {
        type int32;
      }
    }
    container SFPList {
      leaf-list SFPList_Entry {
        type int32;
      }
    }
    container LAGList {
      leaf-list LAGList_Entry {
        type int32;
      }
    }
  }
  /* cpss/device.proto */
  grouping DevicePortEntry {
    leaf DeviceID {
      type int32;
    }
    leaf PortNo {
      type int32;
    }
  }
  /* cpss/device.proto */
  grouping DevicePortList {
    container List {
      list List_Entry {
        uses DevicePortEntry;
      }
    }
  }
  /* cpss/device.proto */
  grouping DeviceTrunkEntry {
    leaf DeviceID {
      type int32;
    }
    leaf TrunkID {
      type int32;
    }
  }
  /* cpss/device.proto */
  grouping DeviceTrunkList {
    container List {
      list List_Entry {
        uses DeviceTrunkEntry;
      }
    }
  }
  /* cpss/device.proto */
  grouping DeviceInterfaceEntry {
    leaf Type {
      type InterfaceTypeOptions;
    }
    leaf DeviceID {
      type int32;
    }
    leaf PortNo {
      type int32;
    }
    leaf LAGNo {
      type int32;
    }
  }
  /* cpss/device.proto */
  grouping DeviceInterfaceList {
    container List {
      list List_Entry {
        uses DeviceInterfaceEntry;
      }
    }
  }
  /* cpss/trunking.proto */
  grouping TrunkingGroupMemberEntry {
    leaf LAGNo {
      type int32;
    }
    container EnableMemberList {
      uses DevicePortList;
    }
    container DisableMemberList {
      uses DevicePortList;
    }
  }
  /* cpss/trunking.proto */
  grouping TrunkingMemberEntry {
    leaf LAGNo {
      type int32;
    }
    container MemberList {
      uses DevicePortList;
    }
  }
  /* cpss/trunking.proto */
  grouping TrunkingGroupID {
    leaf LAGNo {
      type int32;
    }
  }
  /* cpss/trunking.proto */
  grouping TrunkingLoadBalanceMode {
    leaf Mode {
      type TrunkingLoadBalanceModeOptions;
    }
  }
  /* cpss/acl.proto */
  grouping ACLIndexList {
    container List {
      leaf-list List_Entry {
        type int32;
      }
    }
  }
  /* cpss/acl.proto */
  grouping ACLUserDefinedRuleList {
    container List {
      list List_Entry {
        uses ACLUserDefinedRuleEntry;
      }
    }
  }
  /* cpss/acl.proto */
  grouping ACLUserDefinedRuleEntry {
    leaf Index {
      type int32;
    }
    leaf UniqueID {
      type string;
    }
    leaf DirectionType {
      type ACLDirectionTypeOptions;
    }
    leaf Type {
      type ACLRuleTypeOptions;
    }
    leaf SourceMAC {
      type string;
    }
    leaf SourceMACMask {
      type string;
    }
    leaf DestinationMAC {
      type string;
    }
    leaf DestinationMACMask {
      type string;
    }
    leaf EtherType {
      type int32;
    }
    leaf EtherTypeMask {
      type int32;
    }
    leaf SourceIPAddr {
      type string;
    }
    leaf SourceIPMask {
      type string;
    }
    leaf DestinationIPAddr {
      type string;
    }
    leaf DestinationIPMask {
      type string;
    }
    leaf IPProtocol {
      type int32;
    }
    leaf IPProtocolMask {
      type int32;
    }
    leaf L4SourcePort {
      type int32;
    }
    leaf L4SourcePortMask {
      type int32;
    }
    leaf L4DestinationPort {
      type int32;
    }
    leaf L4DestinationPortMask {
      type int32;
    }
    leaf VlanID {
      type int32;
    }
    container SourceInterface {
      uses ACLSourceInterfaceEntry;
    }
    container Action {
      uses ACLActionEntry;
    }
  }
  /* cpss/acl.proto */
  grouping ACLUserDefinedRuleRemovalList {
    container List {
      list List_Entry {
        uses ACLUserDefinedRuleRemovalEntry;
      }
    }
  }
  /* cpss/acl.proto */
  grouping ACLUserDefinedRuleRemovalEntry {
    leaf Index {
      type int32;
    }
    leaf UniqueID {
      type string;
    }
  }
  /* cpss/acl.proto */
  grouping ACLControlRuleEntry {
    leaf Type {
      type ACLRuleTypeOptions;
    }
    leaf Index {
      type int32;
    }
    choice Rule {
      container MACIPBindingRule {
        uses ACLMACIPBindingRuleEntry;
      }
      container SubnetBasedRule {
        uses ACLSubnetBasedRuleEntry;
      }
      container MACBasedRule {
        uses ACLMACBasedRuleEntry;
      }
      container SelectiveQinQRule {
        uses ACLSelectiveQinQRuleEntry;
      }
      container FlowMirrorRule {
        uses ACLFlowMirrorRuleEntry;
      }
      container MACCountingRule {
        uses ACLMACCountingRuleEntry;
      }
      container PTPMessageRule {
        uses ACLPTPMessageRuleEntry;
      }
    }
    container SourceInterface {
      uses ACLSourceInterfaceEntry;
    }
    container Action {
      uses ACLActionEntry;
    }
  }
  /* cpss/acl.proto */
  grouping ACLSourceInterfaceEntry {
    leaf Type {
      type InterfaceTypeOptions;
    }
    leaf VlanID {
      type int32;
    }
    container PortList {
      list PortList_Entry {
        uses DevicePortEntry;
      }
    }
    container LAGList {
      list LAGList_Entry {
        uses TrunkingGroupID;
      }
    }
  }
  /* cpss/acl.proto */
  grouping ACLActionEntry {
    leaf PacketCommand {
      type PacketCommandOptions;
    }
  }
  /* cpss/acl.proto */
  grouping ACLG8032RuleEntry {
    leaf RingID {
      type int32;
    }
    leaf VlanID {
      type int32;
    }
    leaf DestinationRingPort {
      type int32;
    }
  }
  /* cpss/acl.proto */
  grouping ACLMACIPBindingRuleEntry {
    leaf SourceMAC {
      type string;
    }
    leaf SourceIPAddr {
      type string;
    }
  }
  /* cpss/acl.proto */
  grouping ACLSubnetBasedRuleEntry {
    leaf SourceIPAddr {
      type string;
    }
    leaf SourceIPMask {
      type string;
    }
    leaf ModifyVlanID {
      type int32;
    }
  }
  /* cpss/acl.proto */
  grouping ACLMACBasedRuleEntry {
    leaf SourceMAC {
      type string;
    }
    leaf SourceMACMask {
      type string;
    }
    leaf ModifyVlanID {
      type int32;
    }
  }
  /* cpss/acl.proto */
  grouping ACLSelectiveQinQRuleEntry {
    leaf VlanFrom {
      type int32;
    }
    leaf VlanTo {
      type int32;
    }
  }
  /* cpss/acl.proto */
  grouping ACLFlowMirrorRuleEntry {
    leaf IsMirrorEnabled {
      type boolean;
    }
    container Flow {
      uses ACLUserDefinedRuleEntry;
    }
  }
  /* cpss/acl.proto */
  grouping ACLMACCountingRuleEntry {
    leaf CNCCounterIndex {
      type int32;
    }
    leaf SourceMAC {
      type string;
    }
  }
  /* cpss/acl.proto */
  grouping ACLPTPMessageRuleEntry {
    leaf EtherType {
      type int32;
    }
  }
  /* cpss/cnc.proto */
  grouping CNCCountingEntry {
    leaf Type {
      type CNCCountingTypeOptions;
    }
    choice Entry {
      container MACAddressCountingEntry {
        uses CNCMACAddressCountingEntry;
      }
    }
  }
  /* cpss/cnc.proto */
  grouping CNCMACAddressCountingEntry {
    container Address {
      uses MACAddress;
    }
  }
  /* cpss/cnc.proto */
  grouping CNCCounter {
    leaf ByteCount {
      type uint64;
    }
    leaf PktCount {
      type uint64;
    }
  }
  /* cpss/fdb.proto */
  grouping FDBAutoLearningEnable {
    leaf Enable {
      type boolean;
    }
  }
  /* cpss/fdb.proto */
  grouping FDBIdentifyEntry {
    leaf VlanID {
      type int32;
    }
    leaf Address {
      type string;
    }
  }
  /* cpss/fdb.proto */
  grouping FDBSecureBreachEntry {
    container Port {
      uses DevicePortEntry;
    }
    leaf Enable {
      type boolean;
    }
  }
  /* cpss/fdb.proto */
  grouping FDBMACEntry {
    leaf InterfaceType {
      type InterfaceTypeOptions;
    }
    leaf IsStatic {
      type boolean;
    }
    leaf IsForward {
      type boolean;
    }
    leaf VlanID {
      type int32;
    }
    leaf Address {
      type string;
    }
    container Port {
      uses DevicePortEntry;
    }
    container Trunk {
      uses DeviceTrunkEntry;
    }
    container Multicast {
      uses FDBMulticastEntry;
    }
    leaf Action {
      type FDBEntryActionTypeOptions;
    }
  }
  /* cpss/fdb.proto */
  grouping FDBDumpEntry {
    container List {
      list List_Entry {
        uses FDBMACEntry;
      }
    }
  }
  /* cpss/fdb.proto */
  grouping FDBHashEntry {
    leaf LayerType {
      type FDBLayerTypeOptions;
    }
    leaf VlanID {
      type int32;
    }
    leaf Address {
      type string;
    }
  }
  /* cpss/fdb.proto */
  grouping FDBAgingTime {
    leaf Time {
      type int32;
    }
  }
  /* cpss/fdb.proto */
  grouping FDBFlushEntry {
    leaf InterfaceType {
      type InterfaceTypeOptions;
    }
    leaf IsUnicastDynamic {
      type boolean;
    }
    leaf IsUnicastAll {
      type boolean;
    }
    leaf IsMulticast {
      type boolean;
    }
    container VlanList {
      leaf-list VlanList_Entry {
        type int32;
      }
    }
    container PortList {
      uses DevicePortList;
    }
    container TrunkList {
      uses DeviceTrunkList;
    }
  }
  /* cpss/fdb.proto */
  grouping FDBMulticastEntry {
    leaf EntryType {
      type MulticastEntryTypeOptions;
    }
    leaf VIDX {
      type int32;
    }
  }
  /* cpss/fdb.proto */
  grouping FDBCounters {
    leaf NumberOfFreeEntries {
      type int32;
    }
    leaf NumberOfUsedEntries {
      type int32;
    }
    leaf NumberOfMacUnicastDynamicEntries {
      type int32;
    }
    leaf NumberOfMacUnicastStaticEntries {
      type int32;
    }
    leaf NumberOfMacMulticastDynamicEntries {
      type int32;
    }
    leaf NumberOfMacMulticastStaticEntries {
      type int32;
    }
    leaf NumberOfIpv4MulticastEntries {
      type int32;
    }
    leaf NumberOfIpv6MulticastEntries {
      type int32;
    }
  }
  /* cpss/mirroring.proto */
  grouping MirroringSessionEntry {
    leaf SourceType {
      type InterfaceTypeOptions;
    }
    container SourcePortList {
      list SourcePortList_Entry {
        uses MirroringSourcePortEntry;
      }
    }
    container SourceVlanList {
      list SourceVlanList_Entry {
        uses MirroringSourceVlanEntry;
      }
    }
    container DestinationPort {
      uses DevicePortEntry;
    }
    container RSPAN {
      uses MirroringRSPANEntry;
    }
  }
  /* cpss/mirroring.proto */
  grouping MirroringSourcePortEntry {
    leaf Direction {
      type MirroringDirectionTypeOptions;
    }
    container Port {
      uses DevicePortEntry;
    }
  }
  /* cpss/mirroring.proto */
  grouping MirroringSourceVlanEntry {
    leaf Direction {
      type MirroringDirectionTypeOptions;
    }
    leaf VlanID {
      type int32;
    }
  }
  /* cpss/mirroring.proto */
  grouping MirroringSessionList {
    container List {
      list List_Entry {
        uses MirroringSessionEntry;
      }
    }
  }
  /* cpss/mirroring.proto */
  grouping MirroringPolicyBased {
    leaf IsEnabled {
      type boolean;
    }
    container DestinationPort {
      uses DevicePortEntry;
    }
  }
  /* cpss/mirroring.proto */
  grouping MirroringRSPANEntry {
    leaf IsLocalEnabled {
      type boolean;
    }
    leaf IsRemoteEnabled {
      type boolean;
    }
    leaf AnalyzerVlanID {
      type int32;
    }
  }
  /* cpss/misc.proto */
  grouping MiscMACRegisterEntry {
    leaf Address {
      type uint32;
    }
    leaf Data {
      type uint32;
    }
  }
  /* cpss/misc.proto */
  grouping MiscSMIRegisterEntry {
    leaf PHYInterface {
      type uint32;
    }
    leaf PHYID {
      type uint32;
    }
    leaf Address {
      type uint32;
    }
    leaf Data {
      type uint32;
    }
  }
  /* cpss/misc.proto */
  grouping MiscXSMIRegisterEntry {
    leaf PHYInterface {
      type uint32;
    }
    leaf PHYID {
      type uint32;
    }
    leaf PHYDev {
      type uint32;
    }
    leaf Address {
      type uint32;
    }
    leaf Data {
      type uint32;
    }
  }
  /* cpss/misc.proto */
  grouping MiscRegisterData {
    leaf Data {
      type uint32;
    }
  }
  /* cpss/misc.proto */
  grouping MiscTemperature {
    leaf Temperature {
      type int32;
    }
  }
  /* cpss/misc.proto */
  grouping MiscPHYPortModel {
    leaf Interface {
      type string;
    }
    leaf Model {
      type string;
    }
  }
  /* cpss/misc.proto */
  grouping MiscModel {
    leaf Model {
      type string;
    }
  }
  /* cpss/vlan.proto */
  grouping VlanID {
    leaf VlanID {
      type int32;
    }
  }
  /* cpss/vlan.proto */
  grouping VlanList {
    container List {
      leaf-list List_Entry {
        type int32;
      }
    }
  }
  /* cpss/vlan.proto */
  grouping VlanMemberTaggingList {
    leaf VlanID {
      type int32;
    }
    container List {
      list List_Entry {
        uses VlanMemeberTaggingEntry;
      }
    }
  }
  /* cpss/vlan.proto */
  grouping VlanMemeberTaggingEntry {
    container Interface {
      uses DeviceInterfaceEntry;
    }
    leaf Command {
      type VlanTaggingCommandTypeOptions;
    }
  }
  /* cpss/vlan.proto */
  grouping VlanDefaultVIDEntry {
    leaf VlanID {
      type int32;
    }
    container Interface {
      uses DeviceInterfaceEntry;
    }
  }
  /* cpss/vlan.proto */
  grouping VlanAcceptFrameTypeEntry {
    container Interface {
      uses DeviceInterfaceEntry;
    }
    leaf Type {
      type VlanAcceptFrameTypeOptions;
    }
  }
  /* cpss/vlan.proto */
  grouping VlanTPIDIndexEntry {
    container Interface {
      uses DeviceInterfaceEntry;
    }
    leaf Index {
      type int32;
    }
  }
  /* cpss/vlan.proto */
  grouping VlanTPIDEntry {
    leaf Index {
      type int32;
    }
    leaf TPID {
      type int32;
    }
  }
  /* cpss/vlan.proto */
  grouping VlanTPIDList {
    container List {
      list List_Entry {
        uses VlanTPIDEntry;
      }
    }
  }
  /* cpss/vlan.proto */
  grouping VlanStatusEntry {
    leaf VlanID {
      type int32;
    }
    container UntaggedList {
      leaf-list UntaggedList_Entry {
        type int32;
      }
    }
    container TaggedList {
      leaf-list TaggedList_Entry {
        type int32;
      }
    }
    container ProviderList {
      leaf-list ProviderList_Entry {
        type int32;
      }
    }
    container CustomerList {
      leaf-list CustomerList_Entry {
        type int32;
      }
    }
  }
  /* cpss/vlan.proto */
  grouping VlanStatusList {
    container List {
      list List_Entry {
        uses VlanStatusEntry;
      }
    }
  }
  /* cpss/vlan.proto */
  grouping VlanFlushEntry {
    leaf IsFlushAll {
      type boolean;
    }
    leaf VlanID {
      type int32;
    }
  }
  /* cpss/vlan.proto */
  grouping VlanTunnelEntry {
    container Interface {
      uses DeviceInterfaceEntry;
    }
    leaf IsEnabled {
      type boolean;
    }
  }
  /* cpss/vlan.proto */
  grouping VlanProtocolClassID {
    leaf ClassID {
      type int32;
    }
  }
  /* cpss/vlan.proto */
  grouping VlanProtocolClassEntry {
    leaf ClassID {
      type int32;
    }
    leaf EtherType {
      type int32;
    }
    leaf Encapsulation {
      type VlanProtocolBasedEncapsulationTypeOptions;
    }
  }
  /* cpss/vlan.proto */
  grouping VlanProtocolEntry {
    container Interface {
      uses DeviceInterfaceEntry;
    }
    leaf ClassID {
      type int32;
    }
    leaf VlanID {
      type int32;
    }
  }
  /* cpss/vlan.proto */
  grouping VlanTranslationEntry {
    container Interface {
      uses DeviceInterfaceEntry;
    }
    leaf IsEnabled {
      type boolean;
    }
  }
  /* cpss/vlan.proto */
  grouping VlanTranslationMappingEntry {
    leaf SourceVlanID {
      type int32;
    }
    leaf TranslatedVlanID {
      type int32;
    }
  }
  /* cpss/multicast.proto */
  grouping MulticastBridgeGroupEntry {
    container Identify {
      uses FDBIdentifyEntry;
    }
    container InterfaceList {
      list InterfaceList_Entry {
        uses DeviceInterfaceEntry;
      }
    }
  }
  /* cpss/multicast.proto */
  grouping MulticastUnregisteredFloodingEntry {
    leaf VlanID {
      type int32;
    }
    container InterfaceList {
      list InterfaceList_Entry {
        uses DeviceInterfaceEntry;
      }
    }
  }
  /* cpss/multicast.proto */
  grouping MulticastTableVlanFloodingEntry {
    leaf VlanID {
      type int32;
    }
    leaf VIDX {
      type int32;
    }
    container PortList {
      list PortList_Entry {
        uses DevicePortEntry;
      }
    }
  }
  /* cpss/multicast.proto */
  grouping MulticastTableBridgeGroupEntry {
    leaf VlanID {
      type int32;
    }
    leaf VIDX {
      type int32;
    }
    leaf Address {
      type string;
    }
    container PortList {
      list PortList_Entry {
        uses DevicePortEntry;
      }
    }
  }
  /* cpss/multicast.proto */
  grouping MulticastTable {
    container VlanFloodingList {
      list VlanFloodingList_Entry {
        uses MulticastTableVlanFloodingEntry;
      }
    }
    container BridgeGroupList {
      list BridgeGroupList_Entry {
        uses MulticastTableBridgeGroupEntry;
      }
    }
  }
  /* cpss/packetControl.proto */
  grouping PacketControlActionEntry {
    leaf Enable {
      type boolean;
    }
    leaf VlanID {
      type int32;
    }
    container Port {
      uses DevicePortEntry;
    }
  }
  /* cpss/packetControl.proto */
  grouping PacketControlGeneralStatusEntry {
    leaf Protocol {
      type PacketControlProtocolTypeOptions;
    }
    leaf IsEnabled {
      type boolean;
    }
    leaf PacketCommand {
      type PacketCommandOptions;
    }
  }
  /* cpss/packetControl.proto */
  grouping PacketControlInterfaceStatusEntry {
    leaf Protocol {
      type PacketControlProtocolTypeOptions;
    }
    leaf Type {
      type InterfaceTypeOptions;
    }
    container EnabledList {
      leaf-list EnabledList_Entry {
        type int32;
      }
    }
    leaf PacketCommand {
      type PacketCommandOptions;
    }
  }
  /* cpss/packetControl.proto */
  grouping PacketControlStatusList {
    container GeneralList {
      list GeneralList_Entry {
        uses PacketControlGeneralStatusEntry;
      }
    }
    container InterfaceList {
      list InterfaceList_Entry {
        uses PacketControlInterfaceStatusEntry;
      }
    }
  }
  /* cpss/policer.proto */
  grouping PolicerStormCountingEnableEntry {
    leaf IsEnable {
      type boolean;
    }
    container Port {
      uses DevicePortEntry;
    }
  }
  /* cpss/policer.proto */
  grouping PolicerStormCountingCounterEntry {
    leaf UnknownUnicastByteCount {
      type uint64;
    }
    leaf UnknownUnicastPktCount {
      type uint64;
    }
    leaf MulticastByteCount {
      type uint64;
    }
    leaf MulticastPktCount {
      type uint64;
    }
    leaf BroadcastByteCount {
      type uint64;
    }
    leaf BroadcastPktCount {
      type uint64;
    }
  }
  /* cpss/port.proto */
  grouping PortEnableEntry {
    container Port {
      uses DevicePortEntry;
    }
    leaf Enable {
      type boolean;
    }
    leaf Speed {
      type PortSpeedDuplexOptions;
    }
  }
  /* cpss/port.proto */
  grouping PortSpeedDuplexEntry {
    container Port {
      uses DevicePortEntry;
    }
    leaf Speed {
      type PortSpeedDuplexOptions;
    }
  }
  /* cpss/port.proto */
  grouping PortSpeedDuplexList {
    container List {
      list List_Entry {
        uses PortSpeedDuplexEntry;
      }
    }
  }
  /* cpss/port.proto */
  grouping PortFlowControlEntry {
    container Port {
      uses DevicePortEntry;
    }
    leaf Enable {
      type boolean;
    }
  }
  /* cpss/port.proto */
  grouping PortEEEEntry {
    container Port {
      uses DevicePortEntry;
    }
    leaf Enable {
      type boolean;
    }
  }
  /* cpss/port.proto */
  grouping PortCounterEntry {
    container Port {
      uses DevicePortEntry;
    }
    leaf GoodOctetsRecv {
      type uint64;
    }
    leaf BadOctetsRecv {
      type uint64;
    }
    leaf MACTransmitErr {
      type uint64;
    }
    leaf GoodPktsRecv {
      type uint64;
    }
    leaf BadPktsRecv {
      type uint64;
    }
    leaf BrdcPktsRecv {
      type uint64;
    }
    leaf McPktsRecv {
      type uint64;
    }
    leaf Pkts_64Octets {
      type uint64;
    }
    leaf Pkts_65To_127Octets {
      type uint64;
    }
    leaf Pkts_128To_255Octets {
      type uint64;
    }
    leaf Pkts_256To_511Octets {
      type uint64;
    }
    leaf Pkts_512To_1023Octets {
      type uint64;
    }
    leaf Pkts_1024ToMaxOctets {
      type uint64;
    }
    leaf GoodOctetsSent {
      type uint64;
    }
    leaf GoodPktsSent {
      type uint64;
    }
    leaf ExcessiveCollisions {
      type uint64;
    }
    leaf McPktsSent {
      type uint64;
    }
    leaf BrdcPktsSent {
      type uint64;
    }
    leaf UnrecogMACCntrRecv {
      type uint64;
    }
    leaf FCSent {
      type uint64;
    }
    leaf GoodFCRecv {
      type uint64;
    }
    leaf DropEvents {
      type uint64;
    }
    leaf UndersizePkts {
      type uint64;
    }
    leaf FragmentsPkts {
      type uint64;
    }
    leaf OversizePkts {
      type uint64;
    }
    leaf JabberPkts {
      type uint64;
    }
    leaf MACRecvError {
      type uint64;
    }
    leaf BadCrc {
      type uint64;
    }
    leaf Collisions {
      type uint64;
    }
    leaf LateCollisions {
      type uint64;
    }
    leaf BadFcRecv {
      type uint64;
    }
    leaf UcPktsRecv {
      type uint64;
    }
    leaf UcPktsSent {
      type uint64;
    }
    leaf MultiplePktsSent {
      type uint64;
    }
    leaf DeferredPktsSent {
      type uint64;
    }
  }
  /* cpss/port.proto */
  grouping PortCounterList {
    container List {
      list List_Entry {
        uses PortCounterEntry;
      }
    }
  }
  /* cpss/port.proto */
  grouping PortIsolationEntry {
    container Port {
      uses DevicePortEntry;
    }
    container OutgoingList {
      list OutgoingList_Entry {
        uses DevicePortEntry;
      }
    }
  }
  /* cpss/port.proto */
  grouping PortIsolationList {
    container List {
      list List_Entry {
        uses PortIsolationEntry;
      }
    }
  }
  /* cpss/port.proto */
  grouping PortIPGSize {
    leaf Size {
      type int32;
    }
  }
  /* cpss/port.proto */
  grouping PortFaultStatusEntry {
    leaf IsRxFault {
      type boolean;
    }
    leaf IsTxFault {
      type boolean;
    }
  }
  /* cpss/port.proto */
  grouping PortStatusEntry {
    container Port {
      uses DevicePortEntry;
    }
    leaf IsEnabled {
      type boolean;
    }
    leaf IsLinkUp {
      type boolean;
    }
    leaf IsFlowControlEnabled {
      type boolean;
    }
    leaf LinkSpeed {
      type PortSpeedDuplexOptions;
    }
    leaf EEEActive {
      type boolean;
    }
    leaf PMState {
      type string;
    }
  }
  /* cpss/ptp.proto */
  grouping PTPToD {
    leaf Sec {
      type uint64;
    }
    leaf Ns {
      type uint32;
    }
  }
  /* cpss/ptp.proto */
  grouping PTPToDFrequency {
    leaf FractionalNs {
      type uint32;
    }
  }
  /* cpss/ptp.proto */
  grouping PTPQueueInfo {
    leaf Sec {
      type uint64;
    }
    leaf Ns {
      type uint32;
    }
  }
  /* cpss/ptp.proto */
  grouping PTPMessageInfo {
    container Port {
      uses DevicePortEntry;
    }
    leaf SeqID {
      type uint32;
    }
    leaf MessageType {
      type uint32;
    }
    leaf QueueNo {
      type uint32;
    }
  }
  /* cpss/ptp.proto */
  grouping PTPLinkDelay {
    container Port {
      uses DevicePortEntry;
    }
    leaf Delay {
      type int32;
    }
  }
  /* cpss/ptp.proto */
  grouping PTPPortDelay {
    container Port {
      uses DevicePortEntry;
    }
    leaf Direction {
      type PTPPortDelayTypeOptions;
    }
    leaf Delay {
      type int32;
    }
  }
  /* cpss/ptp.proto */
  grouping PTPMode {
    container Port {
      uses DevicePortEntry;
    }
    leaf DomainIndex {
      type uint32;
    }
    leaf DomainNumber {
      type uint32;
    }
    leaf Mode {
      type PTPModeTypeOptions;
    }
  }
  /* cpss/ptp.proto */
  grouping PTPSyncE {
    container Port {
      uses DevicePortEntry;
    }
    leaf IsEnable {
      type boolean;
    }
    leaf Speed {
      type PortSpeedDuplexOptions;
    }
    leaf ClockSelect {
      type PTPSyncERecoveryClockSelectTypeOptions;
    }
  }
  /* cpss/qos.proto */
  grouping QoSPortProfileEntry {
    container Port {
      uses DevicePortEntry;
    }
    leaf Mode {
      type QoSTrustModeOptions;
    }
  }
  /* cpss/qos.proto */
  grouping QoSPortProfileList {
    container List {
      list List_Entry {
        uses QoSPortProfileEntry;
      }
    }
  }
  /* cpss/qos.proto */
  grouping QoSPortQueueList {
    container List {
      list List_Entry {
        uses QoSPortQueueEntry;
      }
    }
  }
  /* cpss/qos.proto */
  grouping QoSPortQueueEntry {
    leaf QueueNo {
      type int32;
    }
    leaf Ratio {
      type int32;
    }
    leaf Scheduler {
      type QoSSchedulerTypeOptions;
    }
  }
  /* cpss/qos.proto */
  grouping QoSCoSProfile {
    leaf CoSNo {
      type int32;
    }
    leaf QueueNo {
      type int32;
    }
  }
  /* cpss/qos.proto */
  grouping QoSCoSProfileList {
    container CoSList {
      list CoSList_Entry {
        uses QoSCoSProfile;
      }
    }
  }
  /* cpss/qos.proto */
  grouping QoSDSCPProfile {
    leaf DSCPNo {
      type int32;
    }
    leaf QueueNo {
      type int32;
    }
  }
  /* cpss/qos.proto */
  grouping QoSDSCPProfileList {
    container DSCPList {
      list DSCPList_Entry {
        uses QoSDSCPProfile;
      }
    }
  }
  /* cpss/ratelimiting.proto */
  grouping RateLimitingIngressEntry {
    container FilterTypes {
      leaf-list FilterTypes_Entry {
        type RateLimitingIngressFilterTypeOptions;
      }
    }
    container Port {
      uses DevicePortEntry;
    }
    leaf Rate {
      type int32;
    }
  }
  /* cpss/ratelimiting.proto */
  grouping RateLimitingIngressList {
    container List {
      list List_Entry {
        uses RateLimitingIngressEntry;
      }
    }
  }
  /* cpss/ratelimiting.proto */
  grouping RateLimitingEgressEntry {
    container Port {
      uses DevicePortEntry;
    }
    leaf Rate {
      type int32;
    }
  }
  /* cpss/ratelimiting.proto */
  grouping RateLimitingEgressList {
    container List {
      list List_Entry {
        uses RateLimitingEgressEntry;
      }
    }
  }
  /* cpss/stp.proto */
  grouping STPID {
    leaf ID {
      type int32;
    }
    leaf Proto {
      type STPProtocolTypeOptions;
    }
  }
  /* cpss/stp.proto */
  grouping STPPortState {
    leaf ID {
      type int32;
    }
    container IdentifyNo {
      uses DeviceInterfaceEntry;
    }
    leaf State {
      type STPPortStateTypeOptions;
    }
    leaf InActive {
      type boolean;
    }
    leaf Proto {
      type STPProtocolTypeOptions;
    }
  }
  /* cpss/stp.proto */
  grouping STPVlanBinding {
    leaf ID {
      type int32;
    }
    leaf Proto {
      type STPProtocolTypeOptions;
    }
    container VlanList {
      leaf-list VlanList_Entry {
        type int32;
      }
    }
  }
  /* cpss/stp.proto */
  grouping STPIDState {
    leaf ID {
      type int32;
    }
    leaf State {
      type STPPortStateTypeOptions;
    }
    leaf Proto {
      type STPProtocolTypeOptions;
    }
  }


  /* **************************************************************************************************
   * Services    : 16                                                                                 *
   ************************************************************************************************** */

  /* **************************************************************************************************
   * Service     : Device                                                                             *
   * Methods     : 2                                                                                  *
   ************************************************************************************************** */
  /* cpss/device.proto */
  rpc intri-cpss-RunCPSSInit {
  }
  /* cpss/device.proto */
  rpc intri-cpss-GetArchitecture {
    output  {
      uses DeviceArchitecture;
    }
  }

  /* **************************************************************************************************
   * Service     : Trunking                                                                           *
   * Methods     : 6                                                                                  *
   ************************************************************************************************** */
  /* cpss/trunking.proto */
  rpc intri-cpss-SetGroup {
    input  {
      uses TrunkingGroupMemberEntry;
    }
  }
  /* cpss/trunking.proto */
  rpc intri-cpss-AddGroup {
    input  {
      uses TrunkingMemberEntry;
    }
  }
  /* cpss/trunking.proto */
  rpc intri-cpss-DeleteGroup {
    input  {
      uses TrunkingMemberEntry;
    }
  }
  /* cpss/trunking.proto */
  rpc intri-cpss-SetLoadBalanceMode {
    input  {
      uses TrunkingLoadBalanceMode;
    }
  }
  /* cpss/trunking.proto */
  rpc intri-cpss-GetLoadBalanceMode {
    output  {
      uses TrunkingLoadBalanceMode;
    }
  }
  /* cpss/trunking.proto */
  rpc intri-cpss-GetGroup {
    input  {
      uses TrunkingGroupID;
    }
    output  {
      uses TrunkingGroupMemberEntry;
    }
  }

  /* **************************************************************************************************
   * Service     : ACL                                                                                *
   * Methods     : 8                                                                                  *
   ************************************************************************************************** */
  /* cpss/acl.proto */
  rpc intri-cpss-RunClearAllRules {
  }
  /* cpss/acl.proto */
  rpc intri-cpss-UpdateControlRule {
    input  {
      uses ACLControlRuleEntry;
    }
  }
  /* cpss/acl.proto */
  rpc intri-cpss-AddControlRule {
    input  {
      uses ACLControlRuleEntry;
    }
  }
  /* cpss/acl.proto */
  rpc intri-cpss-DeleteControlRule {
    input  {
      uses ACLControlRuleEntry;
    }
  }
  /* cpss/acl.proto */
  rpc intri-cpss-RunClearControlRule {
    input  {
      uses ACLControlRuleEntry;
    }
  }
  /* cpss/acl.proto */
  rpc intri-cpss-AddUserDefinedRules {
    input  {
      uses ACLUserDefinedRuleList;
    }
  }
  /* cpss/acl.proto */
  rpc intri-cpss-DeleteUserDefinedRules {
    input  {
      uses ACLUserDefinedRuleRemovalList;
    }
  }
  /* cpss/acl.proto */
  rpc intri-cpss-RunClearAllUserDefinedRules {
  }

  /* **************************************************************************************************
   * Service     : CNC                                                                                *
   * Methods     : 3                                                                                  *
   ************************************************************************************************** */
  /* cpss/cnc.proto */
  rpc intri-cpss-AddCounting {
    input  {
      uses CNCCountingEntry;
    }
  }
  /* cpss/cnc.proto */
  rpc intri-cpss-DeleteCounting {
    input  {
      uses CNCCountingEntry;
    }
  }
  /* cpss/cnc.proto */
  rpc intri-cpss-GetCounter {
    input  {
      uses CNCCountingEntry;
    }
    output  {
      uses CNCCounter;
    }
  }

  /* **************************************************************************************************
   * Service     : FDB                                                                                *
   * Methods     : 10                                                                                 *
   ************************************************************************************************** */
  /* cpss/fdb.proto */
  rpc intri-cpss-SetAutoLearnEnable {
    input  {
      uses FDBAutoLearningEnable;
    }
  }
  /* cpss/fdb.proto */
  rpc intri-cpss-SetEntry {
    input  {
      uses FDBMACEntry;
    }
  }
  /* cpss/fdb.proto */
  rpc intri-cpss-DeleteEntry {
    input  {
      uses FDBMACEntry;
    }
  }
  /* cpss/fdb.proto */
  rpc intri-cpss-SetAgingTime {
    input  {
      uses FDBAgingTime;
    }
  }
  /* cpss/fdb.proto */
  rpc intri-cpss-GetAgingTime {
    output  {
      uses FDBAgingTime;
    }
  }
  /* cpss/fdb.proto */
  rpc intri-cpss-SetSecureBreachNaPortEnable {
    input  {
      uses FDBSecureBreachEntry;
    }
  }
  /* cpss/fdb.proto */
  rpc intri-cpss-GetSecureBreachNaPortEnable {
    input  {
      uses DevicePortEntry;
    }
    output  {
      uses Enabled;
    }
  }
  /* cpss/fdb.proto */
  rpc intri-cpss-GetCounter {
    output  {
      uses FDBCounters;
    }
  }
  /* cpss/fdb.proto */
  rpc intri-cpss-RunFlush {
    input  {
      uses FDBFlushEntry;
    }
  }
  /* cpss/fdb.proto */
  rpc intri-cpss-RunDump {
    output  {
      uses FDBDumpEntry;
    }
  }

  /* **************************************************************************************************
   * Service     : Mirroring                                                                          *
   * Methods     : 3                                                                                  *
   ************************************************************************************************** */
  /* cpss/mirroring.proto */
  rpc intri-cpss-RunClearAll {
  }
  /* cpss/mirroring.proto */
  rpc intri-cpss-SetSessions {
    input  {
      uses MirroringSessionList;
    }
  }
  /* cpss/mirroring.proto */
  rpc intri-cpss-SetPolicyBased {
    input  {
      uses MirroringPolicyBased;
    }
  }

  /* **************************************************************************************************
   * Service     : Misc                                                                               *
   * Methods     : 11                                                                                 *
   ************************************************************************************************** */
  /* cpss/misc.proto */
  rpc intri-cpss-RunMACRegisterWrite {
    input  {
      uses MiscMACRegisterEntry;
    }
  }
  /* cpss/misc.proto */
  rpc intri-cpss-RunMACRegisterRead {
    input  {
      uses MiscMACRegisterEntry;
    }
    output  {
      uses MiscRegisterData;
    }
  }
  /* cpss/misc.proto */
  rpc intri-cpss-RunSMIRegisterWrite {
    input  {
      uses MiscSMIRegisterEntry;
    }
  }
  /* cpss/misc.proto */
  rpc intri-cpss-RunSMIRegisterRead {
    input  {
      uses MiscSMIRegisterEntry;
    }
    output  {
      uses MiscRegisterData;
    }
  }
  /* cpss/misc.proto */
  rpc intri-cpss-RunXSMIRegisterWrite {
    input  {
      uses MiscXSMIRegisterEntry;
    }
  }
  /* cpss/misc.proto */
  rpc intri-cpss-RunXSMIRegisterRead {
    input  {
      uses MiscXSMIRegisterEntry;
    }
    output  {
      uses MiscRegisterData;
    }
  }
  /* cpss/misc.proto */
  rpc intri-cpss-GetCPUTemperature {
    output  {
      uses MiscTemperature;
    }
  }
  /* cpss/misc.proto */
  rpc intri-cpss-GetMACTemperature {
    output  {
      uses MiscTemperature;
    }
  }
  /* cpss/misc.proto */
  rpc intri-cpss-GetPHYPortTemperature {
    input  {
      uses DevicePortEntry;
    }
    output  {
      uses MiscTemperature;
    }
  }
  /* cpss/misc.proto */
  rpc intri-cpss-GetCPUModel {
    output  {
      uses MiscModel;
    }
  }
  /* cpss/misc.proto */
  rpc intri-cpss-GetPHYPortModel {
    input  {
      uses DevicePortEntry;
    }
    output  {
      uses MiscPHYPortModel;
    }
  }

  /* **************************************************************************************************
   * Service     : Vlan                                                                               *
   * Methods     : 28                                                                                 *
   ************************************************************************************************** */
  /* cpss/vlan.proto */
  rpc intri-cpss-AddGroup {
    input  {
      uses VlanID;
    }
  }
  /* cpss/vlan.proto */
  rpc intri-cpss-DeleteGroup {
    input  {
      uses VlanID;
    }
  }
  /* cpss/vlan.proto */
  rpc intri-cpss-AddMember {
    input  {
      uses VlanMemberTaggingList;
    }
  }
  /* cpss/vlan.proto */
  rpc intri-cpss-DeleteMember {
    input  {
      uses VlanMemberTaggingList;
    }
  }
  /* cpss/vlan.proto */
  rpc intri-cpss-UpdateAcceptFrameType {
    input  {
      uses VlanAcceptFrameTypeEntry;
    }
  }
  /* cpss/vlan.proto */
  rpc intri-cpss-GetAcceptFrameType {
    input  {
      uses DeviceInterfaceEntry;
    }
    output  {
      uses VlanAcceptFrameTypeEntry;
    }
  }
  /* cpss/vlan.proto */
  rpc intri-cpss-UpdateDefaultVID {
    input  {
      uses VlanDefaultVIDEntry;
    }
  }
  /* cpss/vlan.proto */
  rpc intri-cpss-GetDefaultVID {
    input  {
      uses DeviceInterfaceEntry;
    }
    output  {
      uses VlanID;
    }
  }
  /* cpss/vlan.proto */
  rpc intri-cpss-RunFlush {
  }
  /* cpss/vlan.proto */
  rpc intri-cpss-GetStatus {
    output  {
      uses VlanStatusList;
    }
  }
  /* cpss/vlan.proto */
  rpc intri-cpss-UpdateTPIDEntry {
    input  {
      uses VlanTPIDEntry;
    }
  }
  /* cpss/vlan.proto */
  rpc intri-cpss-DumpTPIDTable {
    output  {
      uses VlanTPIDList;
    }
  }
  /* cpss/vlan.proto */
  rpc intri-cpss-UpdateTPIDIndex {
    input  {
      uses VlanTPIDIndexEntry;
    }
  }
  /* cpss/vlan.proto */
  rpc intri-cpss-GetTPIDIndex {
    input  {
      uses DeviceInterfaceEntry;
    }
    output  {
      uses VlanTPIDIndexEntry;
    }
  }
  /* cpss/vlan.proto */
  rpc intri-cpss-RunClearTPIDIndex {
    input  {
      uses DeviceInterfaceEntry;
    }
  }
  /* cpss/vlan.proto */
  rpc intri-cpss-SetTunnelEnable {
    input  {
      uses VlanTunnelEntry;
    }
  }
  /* cpss/vlan.proto */
  rpc intri-cpss-GetTunnelEnable {
    input  {
      uses DeviceInterfaceEntry;
    }
    output  {
      uses Enabled;
    }
  }
  /* cpss/vlan.proto */
  rpc intri-cpss-UpdateProtocolClass {
    input  {
      uses VlanProtocolClassEntry;
    }
  }
  /* cpss/vlan.proto */
  rpc intri-cpss-GetProtocolClass {
    input  {
      uses VlanProtocolClassID;
    }
    output  {
      uses VlanProtocolClassEntry;
    }
  }
  /* cpss/vlan.proto */
  rpc intri-cpss-RunClearProtocolClass {
    input  {
      uses VlanProtocolClassID;
    }
  }
  /* cpss/vlan.proto */
  rpc intri-cpss-UpdateProtocol {
    input  {
      uses VlanProtocolEntry;
    }
  }
  /* cpss/vlan.proto */
  rpc intri-cpss-GetProtocol {
    input  {
      uses VlanProtocolEntry;
    }
    output  {
      uses VlanProtocolEntry;
    }
  }
  /* cpss/vlan.proto */
  rpc intri-cpss-RunClearProtocol {
    input  {
      uses VlanProtocolEntry;
    }
  }
  /* cpss/vlan.proto */
  rpc intri-cpss-UpdateTranslationEnable {
    input  {
      uses VlanTranslationEntry;
    }
  }
  /* cpss/vlan.proto */
  rpc intri-cpss-GetTranslationEnable {
    input  {
      uses DeviceInterfaceEntry;
    }
    output  {
      uses Enabled;
    }
  }
  /* cpss/vlan.proto */
  rpc intri-cpss-UpdateTranslationMapping {
    input  {
      uses VlanTranslationMappingEntry;
    }
  }
  /* cpss/vlan.proto */
  rpc intri-cpss-GetTranslationMapping {
    input  {
      uses VlanID;
    }
    output  {
      uses VlanID;
    }
  }
  /* cpss/vlan.proto */
  rpc intri-cpss-RunClearTranslationMapping {
    input  {
      uses VlanID;
    }
  }

  /* **************************************************************************************************
   * Service     : Multicast                                                                          *
   * Methods     : 6                                                                                  *
   ************************************************************************************************** */
  /* cpss/multicast.proto */
  rpc intri-cpss-SetBridgeGroup {
    input  {
      uses MulticastBridgeGroupEntry;
    }
  }
  /* cpss/multicast.proto */
  rpc intri-cpss-DeleteBridgeGroup {
    input  {
      uses FDBIdentifyEntry;
    }
  }
  /* cpss/multicast.proto */
  rpc intri-cpss-SetUnregisteredFlooding {
    input  {
      uses MulticastUnregisteredFloodingEntry;
    }
  }
  /* cpss/multicast.proto */
  rpc intri-cpss-RunClearUnregisteredFlooding {
    input  {
      uses VlanID;
    }
  }
  /* cpss/multicast.proto */
  rpc intri-cpss-RunDump {
    output  {
      uses MulticastTable;
    }
  }
  /* cpss/multicast.proto */
  rpc intri-cpss-RunFlush {
  }

  /* **************************************************************************************************
   * Service     : PacketControl                                                                      *
   * Methods     : 13                                                                                 *
   ************************************************************************************************** */
  /* cpss/packetControl.proto */
  rpc intri-cpss-UpdateSTPControl {
    input  {
      uses PacketControlActionEntry;
    }
  }
  /* cpss/packetControl.proto */
  rpc intri-cpss-UpdateLACPControl {
    input  {
      uses PacketControlActionEntry;
    }
  }
  /* cpss/packetControl.proto */
  rpc intri-cpss-UpdateDot1XControl {
    input  {
      uses PacketControlActionEntry;
    }
  }
  /* cpss/packetControl.proto */
  rpc intri-cpss-UpdateLoopControl {
    input  {
      uses PacketControlActionEntry;
    }
  }
  /* cpss/packetControl.proto */
  rpc intri-cpss-UpdateDHCPv4DiscoverControl {
    input  {
      uses PacketControlActionEntry;
    }
  }
  /* cpss/packetControl.proto */
  rpc intri-cpss-UpdateDHCPv4BroadcastOfferControl {
    input  {
      uses PacketControlActionEntry;
    }
  }
  /* cpss/packetControl.proto */
  rpc intri-cpss-UpdateDHCPv4UDPDestination68Control {
    input  {
      uses PacketControlActionEntry;
    }
  }
  /* cpss/packetControl.proto */
  rpc intri-cpss-UpdateDHCPv4UDPDestination67Control {
    input  {
      uses PacketControlActionEntry;
    }
  }
  /* cpss/packetControl.proto */
  rpc intri-cpss-UpdateARPControl {
    input  {
      uses PacketControlActionEntry;
    }
  }
  /* cpss/packetControl.proto */
  rpc intri-cpss-UpdateIGMPVlanControl {
    input  {
      uses PacketControlActionEntry;
    }
  }
  /* cpss/packetControl.proto */
  rpc intri-cpss-UpdateMLDVlanControl {
    input  {
      uses PacketControlActionEntry;
    }
  }
  /* cpss/packetControl.proto */
  rpc intri-cpss-UpdateGVRPControl {
    input  {
      uses PacketControlActionEntry;
    }
  }
  /* cpss/packetControl.proto */
  rpc intri-cpss-GetStatus {
    output  {
      uses PacketControlStatusList;
    }
  }

  /* **************************************************************************************************
   * Service     : Policer                                                                            *
   * Methods     : 3                                                                                  *
   ************************************************************************************************** */
  /* cpss/policer.proto */
  rpc intri-cpss-SetStormCountingEnable {
    input  {
      uses PolicerStormCountingEnableEntry;
    }
  }
  /* cpss/policer.proto */
  rpc intri-cpss-GetStormCountingEnable {
    input  {
      uses DevicePortEntry;
    }
    output  {
      uses PolicerStormCountingEnableEntry;
    }
  }
  /* cpss/policer.proto */
  rpc intri-cpss-GetStormCountingCounter {
    input  {
      uses DevicePortEntry;
    }
    output  {
      uses PolicerStormCountingCounterEntry;
    }
  }

  /* **************************************************************************************************
   * Service     : Port                                                                               *
   * Methods     : 15                                                                                 *
   ************************************************************************************************** */
  /* cpss/port.proto */
  rpc intri-cpss-SetEnable {
    input  {
      uses PortEnableEntry;
    }
  }
  /* cpss/port.proto */
  rpc intri-cpss-GetEnable {
    input  {
      uses DevicePortEntry;
    }
    output  {
      uses PortEnableEntry;
    }
  }
  /* cpss/port.proto */
  rpc intri-cpss-SetSpeedDuplex {
    input  {
      uses PortSpeedDuplexEntry;
    }
  }
  /* cpss/port.proto */
  rpc intri-cpss-GetSpeedDuplex {
    input  {
      uses DevicePortEntry;
    }
    output  {
      uses PortSpeedDuplexEntry;
    }
  }
  /* cpss/port.proto */
  rpc intri-cpss-SetFlowControl {
    input  {
      uses PortFlowControlEntry;
    }
  }
  /* cpss/port.proto */
  rpc intri-cpss-GetFlowControl {
    input  {
      uses DevicePortEntry;
    }
    output  {
      uses PortFlowControlEntry;
    }
  }
  /* cpss/port.proto */
  rpc intri-cpss-SetEnableEEE {
    input  {
      uses PortEEEEntry;
    }
  }
  /* cpss/port.proto */
  rpc intri-cpss-GetEnableEEE {
    input  {
      uses DevicePortEntry;
    }
    output  {
      uses PortEEEEntry;
    }
  }
  /* cpss/port.proto */
  rpc intri-cpss-GetCounter {
    input  {
      uses DevicePortEntry;
    }
    output  {
      uses PortCounterEntry;
    }
  }
  /* cpss/port.proto */
  rpc intri-cpss-RunClearCounter {
    input  {
      uses DevicePortEntry;
    }
  }
  /* cpss/port.proto */
  rpc intri-cpss-SetIsolation {
    input  {
      uses PortIsolationList;
    }
  }
  /* cpss/port.proto */
  rpc intri-cpss-GetIsolation {
    output  {
      uses PortIsolationList;
    }
  }
  /* cpss/port.proto */
  rpc intri-cpss-GetIPG {
    output  {
      uses PortIPGSize;
    }
  }
  /* cpss/port.proto */
  rpc intri-cpss-GetFaultStatus {
    input  {
      uses DevicePortEntry;
    }
    output  {
      uses PortFaultStatusEntry;
    }
  }
  /* cpss/port.proto */
  rpc intri-cpss-GetStatus {
    input  {
      uses DevicePortEntry;
    }
    output  {
      uses PortStatusEntry;
    }
  }

  /* **************************************************************************************************
   * Service     : PTP                                                                                *
   * Methods     : 11                                                                                 *
   ************************************************************************************************** */
  /* cpss/ptp.proto */
  rpc intri-cpss-SetMode {
    input  {
      uses PTPMode;
    }
  }
  /* cpss/ptp.proto */
  rpc intri-cpss-GetIngrTS {
    input  {
      uses PTPMessageInfo;
    }
    output  {
      uses PTPQueueInfo;
    }
  }
  /* cpss/ptp.proto */
  rpc intri-cpss-GetEgrTS {
    input  {
      uses PTPMessageInfo;
    }
    output  {
      uses PTPQueueInfo;
    }
  }
  /* cpss/ptp.proto */
  rpc intri-cpss-SetLinkDelay {
    input  {
      uses PTPLinkDelay;
    }
  }
  /* cpss/ptp.proto */
  rpc intri-cpss-GetLinkDelay {
    input  {
      uses PTPLinkDelay;
    }
    output  {
      uses PTPLinkDelay;
    }
  }
  /* cpss/ptp.proto */
  rpc intri-cpss-SetEnableSyncE {
    input  {
      uses PTPSyncE;
    }
  }
  /* cpss/ptp.proto */
  rpc intri-cpss-SetToD {
    input  {
      uses PTPToD;
    }
  }
  /* cpss/ptp.proto */
  rpc intri-cpss-GetToD {
    output  {
      uses PTPToD;
    }
  }
  /* cpss/ptp.proto */
  rpc intri-cpss-SetToDFrequency {
    input  {
      uses PTPToDFrequency;
    }
  }
  /* cpss/ptp.proto */
  rpc intri-cpss-SetPortDelay {
    input  {
      uses PTPPortDelay;
    }
  }
  /* cpss/ptp.proto */
  rpc intri-cpss-GetPortDelay {
    input  {
      uses PTPPortDelay;
    }
    output  {
      uses PTPPortDelay;
    }
  }

  /* **************************************************************************************************
   * Service     : QoS                                                                                *
   * Methods     : 8                                                                                  *
   ************************************************************************************************** */
  /* cpss/qos.proto */
  rpc intri-cpss-SetQoSPortProfile {
    input  {
      uses QoSPortProfileList;
    }
  }
  /* cpss/qos.proto */
  rpc intri-cpss-GetQoSPortProfile {
    output  {
      uses QoSPortProfileList;
    }
  }
  /* cpss/qos.proto */
  rpc intri-cpss-SetQoSCoSProfile {
    input  {
      uses QoSCoSProfileList;
    }
  }
  /* cpss/qos.proto */
  rpc intri-cpss-GetQoSCoSProfile {
    output  {
      uses QoSCoSProfileList;
    }
  }
  /* cpss/qos.proto */
  rpc intri-cpss-SetQoSDSCPProfile {
    input  {
      uses QoSDSCPProfileList;
    }
  }
  /* cpss/qos.proto */
  rpc intri-cpss-GetQoSDSCPProfile {
    output  {
      uses QoSDSCPProfileList;
    }
  }
  /* cpss/qos.proto */
  rpc intri-cpss-SetQoSQueueProfile {
    input  {
      uses QoSPortQueueList;
    }
  }
  /* cpss/qos.proto */
  rpc intri-cpss-GetQoSQueueProfile {
    output  {
      uses QoSPortQueueList;
    }
  }

  /* **************************************************************************************************
   * Service     : RateLimiting                                                                       *
   * Methods     : 4                                                                                  *
   ************************************************************************************************** */
  /* cpss/ratelimiting.proto */
  rpc intri-cpss-SetIngress {
    input  {
      uses RateLimitingIngressList;
    }
  }
  /* cpss/ratelimiting.proto */
  rpc intri-cpss-GetIngress {
    output  {
      uses RateLimitingIngressList;
    }
  }
  /* cpss/ratelimiting.proto */
  rpc intri-cpss-SetEgress {
    input  {
      uses RateLimitingEgressList;
    }
  }
  /* cpss/ratelimiting.proto */
  rpc intri-cpss-GetEgress {
    output  {
      uses RateLimitingEgressList;
    }
  }

  /* **************************************************************************************************
   * Service     : STP                                                                                *
   * Methods     : 5                                                                                  *
   ************************************************************************************************** */
  /* cpss/stp.proto */
  rpc intri-cpss-SetPortState {
    input  {
      uses STPPortState;
    }
  }
  /* cpss/stp.proto */
  rpc intri-cpss-GetPortState {
    input  {
      uses STPPortState;
    }
    output  {
      uses STPIDState;
    }
  }
  /* cpss/stp.proto */
  rpc intri-cpss-SetVlanBinding {
    input  {
      uses STPVlanBinding;
    }
  }
  /* cpss/stp.proto */
  rpc intri-cpss-GetVlanBinding {
    input  {
      uses STPID;
    }
    output  {
      uses VlanList;
    }
  }
  /* cpss/stp.proto */
  rpc intri-cpss-RunClearVlanBinding {
    input  {
      uses STPVlanBinding;
    }
  }

}
