module intri-time {
  namespace "intri:intri-time";
  prefix "intri-time";
  import timepb {
    prefix "timepb";
  }
  organization "Intrising Inc.";
  contact "xxx@intrising.com.tw";
  revision 2022-06-14 {
    description "Build date.";
  }
}
