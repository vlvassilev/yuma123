module intri-loop {

  namespace "intri:intri-loop";
  prefix "intri-loop";
  organization "
    Intrising Inc.";
  contact "
    intrising@intrising.com.tw";
  revision 2022-06-24 {
    description "Build date.";
  }

  import intri-device {
    prefix intri-device;
  }
  import intri-timestamp {
    prefix intri-timestamp;
  }
  import intri-empty {
    prefix intri-empty;
  }
  grouping Config {
    container PortList {
      list PortList_Entry {
        uses PortConfigEntry;
      }
    }
  }
  grouping PortConfigEntry {
    container IdentifyNo {
      uses intri-device:InterfaceIdentify;
    }
    leaf Enabled {
      mandatory "true";
      type boolean;
    }
  }
  grouping PortConfig {
    container List {
      list List_Entry {
        uses PortConfigEntry;
      }
    }
  }
  grouping StatusEntry {
    container IdentifyNo {
      uses intri-device:InterfaceIdentify;
    }
    container LastLoopTs {
      uses intri-timestamp:Timestamp;
    }
    leaf LoopCount {
      mandatory "true";
      type int32;
    }
    leaf IsLoopCurrent {
      mandatory "true";
      type boolean;
    }
  }
  grouping Status {
    container List {
      list List_Entry {
        uses StatusEntry;
      }
    }
  }
  rpc intri-loop-Loop-GetStatus {
    output {
      uses Status;
    }
  }
  rpc intri-loop-Loop-GetConfig {
    output {
      uses Config;
    }
  }
  rpc intri-loop-Loop-GetPortConfig {
    output {
      uses PortConfig;
    }
  }
  rpc intri-loop-Loop-UpdatePortConfig {
    input {
      uses PortConfigEntry;
    }
  }
}
