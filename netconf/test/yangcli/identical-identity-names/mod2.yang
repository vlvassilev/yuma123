module mod2 {
  yang-version 1.1;

  namespace "http://yuma123.org/ns/test/yangcli/identical-identity-names/mod2";
  prefix m2;

  import mod1 {
    prefix m1;
  }

  organization
    "yuma123.org";

  description
    'Validation of handling of identities with
     identical names but different module namespace.';

  revision 2018-06-27 {
    description
      "Initial version";
  }

  identity myidentity {
    base "m1:mybase";
  }
}
