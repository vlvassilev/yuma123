// Code generated by protoc-gen-yang. DO NOT EDIT.


/* ****************************************************************************************************
 * Import Path : "github.com/Intrising/intri-type/core/cdp"                                           *
 * Dir Path    : github.com/Intrising/intri-type/core/cdp                                             *
 * Go Package  : cdp                                                                                  *
 * Files       : 3                                                                                    *
 **************************************************************************************************** */
module intri-cdp {

  namespace "intri:intri-cdp";

  prefix "intri-cdp";

  organization "Intrising Inc.";

  contact "intrising@intrising.com.tw";

  revision 2022-06-23 {
    description "Build date.";
  }

  import intri-device {
    prefix intri-device;
  }
  import intri-empty {
    prefix intri-empty;
  }


  /* **************************************************************************************************
   * Enums       : 2                                                                                  *
   ************************************************************************************************** */
  /* core/cdp/common.proto */
  typedef VersionTypeOptions {
    type enumeration {
      enum VERSION_TYPE_V1 {
        description "[V1] Use the CDP V1";
        value 0;
      }
      enum VERSION_TYPE_V2 {
        description "[V2] Use the CDP V2";
        value 1;
      }
    }
  }
  /* core/cdp/common.proto */
  typedef CapabilityTypeOptions {
    type enumeration {
      enum CAPABILITY_TYPE_ROUTER {
        description "[Router] Show the capability as a router";
        value 0;
      }
      enum CAPABILITY_TYPE_TRANSPARENT_BRIDGE {
        description "[Transparent Bridge] Show the capability as a transparent bridge";
        value 1;
      }
      enum CAPABILITY_TYPE_SOURCE_ROUTE_BRIDGE {
        description "[Route Bridge] Show the capability as a route bridge";
        value 2;
      }
      enum CAPABILITY_TYPE_SWITCH {
        description "[Switch] Show the capability as a switch";
        value 3;
      }
      enum CAPABILITY_TYPE_HOST {
        description "[Host] Show the capability as a host";
        value 4;
      }
      enum CAPABILITY_TYPE_IGMP_CAPABLE {
        description "[IGMP] Show the capability as an IGMP capable device";
        value 5;
      }
      enum CAPABILITY_TYPE_REPEATER {
        description "[Repeater] Show the capability as a repeater";
        value 6;
      }
      enum CAPABILITY_TYPE_VOIP_PHONE {
        description "[VoIP Phone] Show the capability as a VoIP Phone";
        value 7;
      }
      enum CAPABILITY_TYPE_REMOTELY_MANAGED_DEVICE {
        description "[Remotely Managed Device] Show the capability as a remotely managed device";
        value 8;
      }
      enum CAPABILITY_TYPE_CVTA_STP_DISPUTE_RESOLUTION_CISCO_VT_CAMERA {
        description "[Camara] Show the capability as a camera";
        value 9;
      }
      enum CAPABILITY_TYPE_TWO_PORT_MAC_REPLY {
        description "[Two Port MAC Replay] Show the capability as a two port MAC reply";
        value 10;
      }
    }
  }


  /* **************************************************************************************************
   * Msgs        : 14                                                                                 *
   ************************************************************************************************** */
  /* core/cdp/cdp.proto */
  grouping Config {
    container SystemConfig {
      uses SystemConfig;
    }
  }
  /* core/cdp/cdp.proto */
  grouping SystemConfig {
    leaf Enabled {
      type boolean;
    }
    leaf TimeToLive {
      type int32;
    }
    leaf MsgTxInterval {
      type int32;
    }
    leaf CDPVersion {
      type VersionTypeOptions;
    }
  }
  /* core/cdp/cdp.proto */
  grouping LocalInfo {
    container List {
      list List_Entry {
        uses LocalInfoEntry;
      }
    }
  }
  /* core/cdp/cdp.proto */
  grouping LocalInfoEntry {
    container IdentifyNo {
      uses intri-device:InterfaceIdentify;
    }
    container PowerAvailable {
      uses PowerAvailable;
    }
    container SystemInfo {
      uses SystemInfo;
    }
    container VoiceVlan {
      uses VoiceVLAN;
    }
    container PortInfo {
      uses PortInfo;
    }
    container Capability {
      leaf-list Capability_Entry {
        type CapabilityTypeOptions;
      }
    }
  }
  /* core/cdp/cdp.proto */
  grouping NeighborInfo {
    container List {
      list List_Entry {
        uses NeighborInfoEntry;
      }
    }
  }
  /* core/cdp/cdp.proto */
  grouping NeighborInfoEntry {
    container IdentifyNo {
      uses RecvIdentifyInfo;
    }
    container SystemInfo {
      uses SystemInfo;
    }
    container PowerAvailable {
      uses PowerAvailable;
    }
    leaf TTL {
      type int64;
    }
    leaf VoIPVlan {
      type int32;
    }
  }
  /* core/cdp/cdp.proto */
  grouping RecvIdentifyInfo {
    container RecvIdentifyNo {
      uses intri-device:InterfaceIdentify;
    }
    leaf PortThroughInterface {
      type string;
    }
    container Capability {
      leaf-list Capability_Entry {
        type CapabilityTypeOptions;
      }
    }
  }
  /* core/cdp/cdp.proto */
  grouping SystemInfo {
    container IP {
      leaf-list IP_Entry {
        type string;
      }
    }
    leaf DeviceID {
      type string;
    }
    leaf Platform {
      type string;
    }
    leaf SystemName {
      type string;
    }
    leaf SoftwareVersion {
      type string;
    }
    leaf CDPVersion {
      type VersionTypeOptions;
    }
  }
  /* core/cdp/cdp.proto */
  grouping VoiceVLAN {
    leaf Data {
      type uint8;
    }
    leaf VoiceVlan {
      type int32;
    }
  }
  /* core/cdp/cdp.proto */
  grouping PortInfo {
    leaf PortThroughInterface {
      type string;
    }
  }
  /* core/cdp/cdp.proto */
  grouping PowerAvailable {
    leaf RequestID {
      type int32;
    }
    leaf ManagementID {
      type int32;
    }
    leaf Allocated {
      type decimal64 {
        fraction-digits 2;
      }
    }
    leaf Supported {
      type decimal64 {
        fraction-digits 2;
      }
    }
  }
  /* core/cdp/cdp.proto */
  grouping NeighborPoe {
    leaf RequestId {
      type int32;
    }
    leaf Allocated {
      type decimal64 {
        fraction-digits 2;
      }
    }
  }
  /* core/cdp/cdp.proto */
  grouping Statistic {
    container List {
      list List_Entry {
        uses StatisticEntry;
      }
    }
  }
  /* core/cdp/cdp.proto */
  grouping StatisticEntry {
    container IdentifyNo {
      uses intri-device:InterfaceIdentify;
    }
    leaf FramesOutV1 {
      type uint64;
    }
    leaf FramesOutV2 {
      type uint64;
    }
    leaf FramesInV1 {
      type uint64;
    }
    leaf FramesInV2 {
      type uint64;
    }
    leaf IllegalChecksum {
      type uint64;
    }
    leaf OtherErrors {
      type uint64;
    }
  }


  /* **************************************************************************************************
   * Services    : 1                                                                                  *
   ************************************************************************************************** */

  /* **************************************************************************************************
   * Service     : CDP                                                                                *
   * Methods     : 6                                                                                  *
   ************************************************************************************************** */
  /* core/cdp/service.proto */
  rpc intri-cdp-GetConfig {
    output  {
      uses Config;
    }
  }
  /* core/cdp/service.proto */
  rpc intri-cdp-SetConfig {
    input  {
      uses Config;
    }
  }
  /* core/cdp/service.proto */
  rpc intri-cdp-GetLocalInfo {
    output  {
      uses LocalInfo;
    }
  }
  /* core/cdp/service.proto */
  rpc intri-cdp-GetNeighborInfo {
    output  {
      uses NeighborInfo;
    }
  }
  /* core/cdp/service.proto */
  rpc intri-cdp-GetStatistic {
    output  {
      uses Statistic;
    }
  }
  /* core/cdp/service.proto */
  rpc intri-cdp-RunClearStatistic {
    input  {
      uses intri-device:PortList;
    }
  }

}
