module mod3 {
  yang-version 1.1;

  namespace "http://yuma123.org/ns/sec5_4/mod3";
  prefix m3;

  import mod1 {
    prefix mod1-import;
  }

  organization
    "yuma123.org";

  description 'sec5_4 Resolving Grouping, Type, and Identity Names.
               Same as mod2 but the typedef is referenced in a
               local grouping.';

  revision 2018-05-22 {
    description
      "Initial version";
  }

  grouping entry-grouping {
    leaf entry {
      type mod1-import:entry-ref;
    }
  }

  container refs {
    list ref {
      key entry;
      uses entry-grouping;
    }
  }
}
