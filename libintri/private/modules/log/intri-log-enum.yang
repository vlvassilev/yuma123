submodule intri-log-enum {
  belongs-to "intri-log" {
    prefix "intri-log-enum";
  }
  revision 2022-06-14 {
    description "Build date.";
  }
  // log/common.proto
  typedef StorageTypeOptions {
    type enumeration {
      enum STORAGE_TYPE_FLASH {
        description "[Flash] Log file is stored in flash";
        value 0;
      }
      enum STORAGE_TYPE_RAM_DISK {
        description "[Ram Disk] Log file is stored in ram disk";
        value 1;
      }
    }
  }
}
