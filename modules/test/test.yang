module test {

    namespace "http://netconfcentral.com/ns/test";
    prefix "t";

    organization
        "Netconf Central";

    contact
        "Andy Bierman";

    description
        "YANG test module 1.";

    revision 2008-11-30 {
        description "Moved draft examples to examples.yang.";
    }

    leaf instance1 {
       type instance-identifier;
    }

    leaf instance2 {
       type instance-identifier {
          require-instance false;
       }
    }

    leaf leafref1 {
       type leafref {
          path "../test2/a2";
          require-instance true;
       }
    }

    leaf leafref2 {
       type leafref {
          path "../test2/a2";
          require-instance false;
       }
    }

    container test1 {
      leaf a { 
         type string {
           length 1..max;
         }
         default "1";
      }
      leaf b { 
        type uint32 {
          range min..32;
        }
      }
      leaf c { type binary; }
      leaf d { 
        type enumeration {
          enum x;
          enum y;
          enum z;
        }
        // mandatory true;
      }
      container e {
        leaf-list ee {
          ordered-by user;
          // min-elements 2;
          max-elements 5;
          type string {
            pattern [a-e][1-9]+;
          }
        }
        leaf eee { 
	    type string; 
            default "test";
        }
      }
      choice f {
        // mandatory true;

        leaf f1 { type string; }
        leaf f2 { type string; }
      }
      choice g {
        mandatory false;

        leaf g1 { type string; mandatory true; }
        leaf g2 { type string; }
        case g3 {
          leaf g3a { type string; mandatory true; }
          leaf g3b { type string; }
        }
      }
    }

    list test2 {
      key a2;
      ordered-by user;
      unique b2;
      leaf a1 { 
         type int8; 
         default 4;
      }
      leaf a2 { 
        type string {
          length 1..5 {
            // error-app-tag some-new-tag;
            error-message 'some new message';
          }
        }
      }
      leaf b2 { 
         type uint32;
         default 5;
      }
    }

   augment /test2 {
      container xxx;
      leaf foo { 
        type string;
        mandatory true;
      }
   }


   list test3 {
      key x;

      list test3deep {
        key "t:yy t:y";

        leaf b { 
          type leafref {
            path "../../x";
          }
        }

        leaf bb { 
          type leafref {
            path "../yy";
          }
        }

        leaf bbb { 
          type leafref {
            path "../deepy/yy1";
          }
        }

        leaf c { 
          type leafref {
            path "../../../test3[x = current()/../b]/test3deep
                 [yy=current()/../bb][y=current()/../bbb]/deepy/yy3";
          }
        }

	leaf y { type string; }

        list deepy {
          config true;
          key yy3;
          leaf yy1 { type instance-identifier; }
          leaf yy2 { type float64; }
          leaf yy3 { type string; }
        }

        list deepz {
          leaf zz1 { type instance-identifier; }
          leaf zz2 { type float64; }
          leaf zz3 { type float32; }
        }

        leaf yy { type float32; }
        leaf yy64 { type float64; }
      }

      leaf b2 { type uint32; }

      leaf-list c2 { 
        type int32;
        min-elements 4;
        max-elements 4;
      }

      leaf x { type string; }

   }


   identity id-A;
   identity id-B;
   identity id-C { base id-A; }
   identity id-D { base id-C; }
   identity id-E { base id-D; }

   leaf idtest {
      type identityref { base id-A; }
   }

   container musttest {
     presence "testing one";
     leaf A { type string; }
     choice B {
       mandatory true;
       case B1 {
         leaf B1leaf { type string; }
         leaf B1num { type int32; }
       }
       case B2 {
         leaf B2leaf { type string; mandatory true; }
       }
    }
  }

}
