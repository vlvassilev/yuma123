// Code generated by protoc-gen-yang. DO NOT EDIT.


/* ****************************************************************************************************
 * Import Path : "github.com/Intrising/intri-type/core/lacp"                                          *
 * Dir Path    : github.com/Intrising/intri-type/core/lacp                                            *
 * Go Package  : lacp                                                                                 *
 * Files       : 3                                                                                    *
 **************************************************************************************************** */
module intri-lacp {

  namespace "intri:intri-lacp";

  prefix "intri-lacp";

  organization "Intrising Inc.";

  contact "intrising@intrising.com.tw";

  revision 2022-06-23 {
    description "Build date.";
  }

  import intri-device {
    prefix intri-device;
  }
  import intri-empty {
    prefix intri-empty;
  }


  /* **************************************************************************************************
   * Enums       : 3                                                                                  *
   ************************************************************************************************** */
  /* core/lacp/common.proto */
  typedef ConfigLinkAggregationTypeOptions {
    type enumeration {
      enum CONFIG_LINK_AGGREGATION_STATIC {
        description "[Static]";
        value 0;
      }
      enum CONFIG_LINK_AGGREGATION_DYNAMIC {
        description "[Dyanmic]";
        value 1;
      }
    }
  }
  /* core/lacp/common.proto */
  typedef ModeTypeOptions {
    type enumeration {
      enum MODE_TYPE_PASSIVE {
        description "[Passive]";
        value 0;
      }
      enum MODE_TYPE_ACTIVE {
        description "[Active]";
        value 1;
      }
    }
  }
  /* core/lacp/common.proto */
  typedef IntervalTypeOptions {
    type enumeration {
      enum INTERVAL_TYPE_SLOW {
        description "[Slow]";
        value 0;
      }
      enum INTERVAL_TYPE_FAST {
        description "[Fast]";
        value 1;
      }
    }
  }


  /* **************************************************************************************************
   * Msgs        : 8                                                                                  *
   ************************************************************************************************** */
  /* core/lacp/lacp.proto */
  grouping Config {
    container System {
      uses SystemConfig;
    }
    container LAG {
      uses LAGConfig;
    }
  }
  /* core/lacp/lacp.proto */
  grouping SystemConfig {
    leaf SystemPriority {
      type int32;
    }
    leaf Mode {
      type ModeTypeOptions;
    }
    leaf TransmitInterval {
      type IntervalTypeOptions;
    }
  }
  /* core/lacp/lacp.proto */
  grouping LAGConfig {
    container Lists {
      list Lists_Entry {
        uses LAGConfigEntry;
      }
    }
  }
  /* core/lacp/lacp.proto */
  grouping LAGConfigEntry {
    leaf TrunkID {
      type int32;
    }
    leaf LacpEnable {
      type ConfigLinkAggregationTypeOptions;
    }
    container Identify {
      uses intri-device:PortList;
    }
  }
  /* core/lacp/lacp.proto */
  grouping Status {
    container PortLists {
      list PortLists_Entry {
        uses StatusEntry;
      }
    }
  }
  /* core/lacp/lacp.proto */
  grouping StatusEntry {
    leaf TrunkID {
      type int32;
    }
    container IdentifyNo {
      uses intri-device:InterfaceIdentify;
    }
    leaf LacpEnable {
      type ConfigLinkAggregationTypeOptions;
    }
    container Actor {
      uses ActorPartnerInfo;
    }
    container Partner {
      uses ActorPartnerInfo;
    }
  }
  /* core/lacp/lacp.proto */
  grouping ActorPartnerInfo {
    container IdentifyNo {
      uses intri-device:InterfaceIdentify;
    }
    leaf PortPriority {
      type int32;
    }
    leaf SystemPriority {
      type int32;
    }
    leaf MACAddress {
      type uint8;
    }
    leaf AdminKey {
      type int32;
    }
    leaf OperKey {
      type int32;
    }
    container Status {
      uses State;
    }
  }
  /* core/lacp/lacp.proto */
  grouping State {
    leaf Activity {
      type boolean;
    }
    leaf Timeout {
      type boolean;
    }
    leaf Aggr {
      type boolean;
    }
    leaf Sync {
      type boolean;
    }
    leaf Collect {
      type boolean;
    }
    leaf Distribute {
      type boolean;
    }
    leaf Defaulted {
      type boolean;
    }
    leaf Expired {
      type boolean;
    }
  }


  /* **************************************************************************************************
   * Services    : 1                                                                                  *
   ************************************************************************************************** */

  /* **************************************************************************************************
   * Service     : LACP                                                                               *
   * Methods     : 6                                                                                  *
   ************************************************************************************************** */
  /* core/lacp/service.proto */
  rpc intri-lacp-GetConfig {
    output  {
      uses Config;
    }
  }
  /* core/lacp/service.proto */
  rpc intri-lacp-SetSystem {
    input  {
      uses SystemConfig;
    }
  }
  /* core/lacp/service.proto */
  rpc intri-lacp-GetSystem {
    output  {
      uses SystemConfig;
    }
  }
  /* core/lacp/service.proto */
  rpc intri-lacp-SetTrunk {
    input  {
      uses LAGConfig;
    }
  }
  /* core/lacp/service.proto */
  rpc intri-lacp-GetTrunk {
    input  {
      uses intri-device:InterfaceIdentify;
    }
    output  {
      uses LAGConfigEntry;
    }
  }
  /* core/lacp/service.proto */
  rpc intri-lacp-GetPortStatus {
    output  {
      uses Status;
    }
  }

}
