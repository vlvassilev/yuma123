// Code generated by protoc-gen-yang. DO NOT EDIT.


/* ****************************************************************************************************
 * Import Path : "github.com/Intrising/intri-type/hardware"                                           *
 * Dir Path    : github.com/Intrising/intri-type/hardware                                             *
 * Go Package  : hardware                                                                             *
 * Files       : 6                                                                                    *
 **************************************************************************************************** */
module intri-hardware {

  namespace "intri:intri-hardware";

  prefix "intri-hardware";

  organization "Intrising Inc.";

  contact "intrising@intrising.com.tw";

  revision 2022-06-23 {
    description "Build date.";
  }

  import intri-device {
    prefix intri-device;
  }
  import intri-timestamp {
    prefix intri-timestamp;
  }
  import intri-event {
    prefix intri-event;
  }
  import intri-empty {
    prefix intri-empty;
  }
  import intri-common {
    prefix intri-common;
  }


  /* **************************************************************************************************
   * Enums       : 15                                                                                 *
   ************************************************************************************************** */
  /* hardware/common.proto */
  typedef PowerTypeOptions {
    type enumeration {
      enum POWER_TYPE_REDUNDANT {
        description "[REDUNDANT] Redundant Power";
        value 0;
      }
      enum POWER_TYPE_GENERAL {
        description "[GENERAL] General Power";
        value 1;
      }
    }
  }
  /* hardware/common.proto */
  typedef LEDModeTypeOptions {
    type enumeration {
      enum LED_MODE_TYPE_DYNAMIC {
        description "[Dynamic] Display static states and blink when data is present on a port.";
        value 0;
      }
      enum LED_MODE_TYPE_STATIC {
        description "[Static] Display static states but do not blink with data.";
        value 1;
      }
      enum LED_MODE_TYPE_QUIET_DISPLAY {
        description "[Quiet Display] Desplay is reduced to sys and on LED,and Port LEDs remain off.";
        value 2;
      }
      enum LED_MODE_TYPE_ALL_DARK {
        description "[All Dark] This mode is not recommended, as the unit may mistakenly be deemed powered down.";
        value 3;
      }
      enum LED_MODE_TYPE_LIGHTSHOW {
        description "[Lightshow] Similar to a led_test but permanent. This may be turned on to easier locate a physical unit among others.";
        value 4;
      }
    }
  }
  /* hardware/common.proto */
  typedef LEDBehaviorModeTypeOptions {
    type enumeration {
      enum LED_BEHAVIOR_MODE_TYPE_LINK1G {
        description "* internal";
        value 0;
      }
      enum LED_BEHAVIOR_MODE_TYPE_LINK5G10G {
        description "* internal";
        value 1;
      }
      enum LED_BEHAVIOR_MODE_TYPE_BLOCKED {
        description "* internal";
        value 2;
      }
      enum LED_BEHAVIOR_MODE_TYPE_REJECT {
        description "* internal";
        value 3;
      }
      enum LED_BEHAVIOR_MODE_TYPE_IDLE {
        description "* internal";
        value 4;
      }
      enum LED_BEHAVIOR_MODE_TYPE_POE {
        description "* internal";
        value 5;
      }
      enum LED_BEHAVIOR_MODE_TYPE_POEPLUS {
        description "* internal";
        value 6;
      }
      enum LED_BEHAVIOR_MODE_TYPE_POEPLUSPLUS {
        description "* internal";
        value 7;
      }
      enum LED_BEHAVIOR_MODE_TYPE_OFF {
        description "* internal";
        value 8;
      }
      enum LED_BEHAVIOR_MODE_TYPE_SYS_NORMAL {
        description "* internal";
        value 9;
      }
      enum LED_BEHAVIOR_MODE_TYPE_SYS_MINOR_ALARM {
        description "* internal";
        value 10;
      }
      enum LED_BEHAVIOR_MODE_TYPE_SYS_MAJOR_ALARM {
        description "* internal";
        value 11;
      }
      enum LED_BEHAVIOR_MODE_TYPE_USER_DEF1 {
        description "* internal";
        value 12;
      }
      enum LED_BEHAVIOR_MODE_TYPE_USER_DEF2 {
        description "* internal";
        value 13;
      }
      enum LED_BEHAVIOR_MODE_TYPE_COLOR_GREEN {
        description "* internal";
        value 14;
      }
      enum LED_BEHAVIOR_MODE_TYPE_COLOR_ORANGE {
        description "* internal";
        value 15;
      }
      enum LED_BEHAVIOR_MODE_TYPE_COLOR_RED {
        description "* internal";
        value 16;
      }
      enum LED_BEHAVIOR_MODE_TYPE_COLOR_BLUE {
        description "* internal";
        value 17;
      }
      enum LED_BEHAVIOR_MODE_TYPE_COLOR_MAGENTA {
        description "* internal";
        value 18;
      }
      enum LED_BEHAVIOR_MODE_TYPE_REQUEST_NMP_IP {
        description "* internal";
        value 19;
      }
      enum LED_BEHAVIOR_MODE_TYPE_FACTORY_DEFAULT_KEEP_NETWORK {
        description "* internal";
        value 20;
      }
      enum LED_BEHAVIOR_MODE_TYPE_FACTORY_DEFAULT_KEEP_NONE {
        description "* internal";
        value 21;
      }
      enum LED_BEHAVIOR_MODE_TYPE_FACTORY_DEFAULT_NO_OPERATION {
        description "* internal";
        value 22;
      }
      enum LED_BEHAVIOR_MODE_TYPE_BLINKING_NORMAL {
        description "* internal blink 1 time a 200 milliseconds.";
        value 23;
      }
      enum LED_BEHAVIOR_MODE_TYPE_BLINKING_SLOW {
        description "* internal blink 1 time a 500 milliseconds.";
        value 24;
      }
      enum LED_BEHAVIOR_MODE_TYPE_BLINKING_FAST {
        description "* internal blink 1 time a 100 milliseconds.";
        value 25;
      }
      enum LED_BEHAVIOR_MODE_TYPE_NA {
        description "* internal This LED is not support";
        value 9999;
      }
    }
  }
  /* hardware/common.proto */
  typedef LEDTypeOptions {
    type enumeration {
      enum LED_TYPE_SYSTEM {
        description "";
        value 0;
      }
      enum LED_TYPE_GPS {
        description "";
        value 1;
      }
      enum LED_TYPE_POEMAX {
        description "";
        value 2;
      }
      enum LED_TYPE_FAN {
        description "";
        value 3;
      }
      enum LED_TYPE_POE {
        description "";
        value 4;
      }
      enum LED_TYPE_SFP {
        description "";
        value 5;
      }
    }
  }
  /* hardware/common.proto */
  typedef PoEPriorityLevelTypeOptions {
    type enumeration {
      enum POE_PRIORITY_LEVEL_TYPE_UNKNOWN {
        description "[Unknown] Priority unknow";
        value 0;
      }
      enum POE_PRIORITY_LEVEL_TYPE_LOW {
        description "[Low] Priority low";
        value 1;
      }
      enum POE_PRIORITY_LEVEL_TYPE_MEDIUM {
        description "[Medium] Priority medium";
        value 2;
      }
      enum POE_PRIORITY_LEVEL_TYPE_HIGH {
        description "[High] Priority high";
        value 3;
      }
    }
  }
  /* hardware/common.proto */
  typedef PoEPortModeTypeOptions {
    type enumeration {
      enum POE_PORT_MODE_TYPE_POE {
        description "[PoE] 802.3af PoE";
        value 0;
      }
      enum POE_PORT_MODE_TYPE_POE_PLUS {
        description "[PoE+] 802.3at PoE+";
        value 1;
      }
      enum POE_PORT_MODE_TYPE_POE_PLUS_PLUS {
        description "[PoE++] 802.3bt PoE++";
        value 2;
      }
      enum POE_PORT_MODE_TYPE_POE_LLDP {
        description "*[PoE LLDP Control] PoE mode is controlled by LLDP";
        value 3;
      }
    }
  }
  /* hardware/common.proto */
  typedef PoEDeterminedClassTypeOptions {
    type enumeration {
      enum POE_DETERMINED_CLASS_TYPE_CLASS0 {
        description "[Class0] Class level 0";
        value 0;
      }
      enum POE_DETERMINED_CLASS_TYPE_CLASS1 {
        description "[Class1] Class level 1";
        value 1;
      }
      enum POE_DETERMINED_CLASS_TYPE_CLASS2 {
        description "[Class2] Class level 2";
        value 2;
      }
      enum POE_DETERMINED_CLASS_TYPE_CLASS3 {
        description "[Class3] Class level 3";
        value 3;
      }
      enum POE_DETERMINED_CLASS_TYPE_CLASS4 {
        description "[Class4] Class level 4";
        value 4;
      }
      enum POE_DETERMINED_CLASS_TYPE_CLASS5 {
        description "[Class5] Class level 5";
        value 5;
      }
      enum POE_DETERMINED_CLASS_TYPE_CLASS6 {
        description "[Class6] Class level 6";
        value 6;
      }
      enum POE_DETERMINED_CLASS_TYPE_CLASS7 {
        description "[Class7] Class level 7";
        value 7;
      }
      enum POE_DETERMINED_CLASS_TYPE_CLASS8 {
        description "[Class8] Class level 8";
        value 8;
      }
      enum POE_DETERMINED_CLASS_TYPE_OVERLOAD {
        description "[Overload] Overload";
        value 9;
      }
      enum POE_DETERMINED_CLASS_TYPE_PROBES_NOT_EQUAL {
        description "[Probes Not Equal] Probes not equal";
        value 10;
      }
      enum POE_DETERMINED_CLASS_TYPE_UNKNOWN {
        description "[Unknown] Unknown";
        value 11;
      }
    }
  }
  /* hardware/common.proto */
  typedef PoEConditionTypeOptions {
    type enumeration {
      enum POE_CONDITION_TYPE_DISABLED {
        description "[Disabled] Disabled";
        value 0;
      }
      enum POE_CONDITION_TYPE_POWER_OFF {
        description "[Power Off] Power off";
        value 1;
      }
      enum POE_CONDITION_TYPE_DTYPECOVERING {
        description "[Dtypecovering] Dtypecovering";
        value 2;
      }
      enum POE_CONDITION_TYPE_POWERED {
        description "[Powered] Powered";
        value 3;
      }
      enum POE_CONDITION_TYPE_CLASS_MTYPEMATCH {
        description "[Class Mtypematch] Class mtypematch";
        value 4;
      }
      enum POE_CONDITION_TYPE_SHORT_CIRCUIT {
        description "[Short Circuit] Short circuit";
        value 5;
      }
      enum POE_CONDITION_TYPE_REJECTED {
        description "[Rejected] Rejected";
        value 6;
      }
      enum POE_CONDITION_TYPE_OVERLOAD {
        description "[Overload] Overload";
        value 7;
      }
      enum POE_CONDITION_TYPE_UNDERLOAD {
        description "[Underload] Underload";
        value 8;
      }
      enum POE_CONDITION_TYPE_OVER_TEMP {
        description "[Over Temperature] Over temperature";
        value 9;
      }
      enum POE_CONDITION_TYPE_VOLTAGE_TOO_LOW {
        description "[Voltage Too Low] Voltage too low";
        value 10;
      }
      enum POE_CONDITION_TYPE_VOLTAGE_TOO_HIGH {
        description "[Voltage Too High] Voltage too high";
        value 11;
      }
      enum POE_CONDITION_TYPE_UNKNOW_ERROR {
        description "[Unknow Error] Unknow error";
        value 12;
      }
      enum POE_CONDITION_TYPE_BUDGET_EXCEEDED {
        description "[Budget Exceeded] Budget exceeded";
        value 13;
      }
      enum POE_CONDITION_TYPE_TYPE_NON_STANDARD_PD {
        description "[None Standard PD Type] None standard PD type";
        value 14;
      }
    }
  }
  /* hardware/common.proto */
  typedef GPSStatusTypeOptions {
    type enumeration {
      enum GPS_STATUS_TYPE_DISABLED {
        description "[Disabled] Disabled";
        value 0;
      }
      enum GPS_STATUS_TYPE_TRACKING {
        description "[Tracking] Tracking";
        value 1;
      }
      enum GPS_STATUS_TYPE_SYNC {
        description "[Sync] Sync";
        value 2;
      }
    }
  }
  /* hardware/dldp.proto */
  typedef DLDPAuthCationModeTypeOptions {
    type enumeration {
      enum DLDP_AUTHCATION_MODE_TYPE_NONE {
        description "";
        value 0;
      }
      enum DLDP_AUTHCATION_MODE_TYPE_PLAINTEXT {
        description "";
        value 1;
      }
      enum DLDP_AUTHCATION_MODE_TYPE_MD5 {
        description "";
        value 2;
      }
    }
  }
  /* hardware/dldp.proto */
  typedef ShutdownModeTypeOptions {
    type enumeration {
      enum SHUT_MODE_TYPE_AUTO {
        description "";
        value 0;
      }
      enum SHUT_MODE_TYPE_MANUAL {
        description "";
        value 1;
      }
    }
  }
  /* hardware/dldp.proto */
  typedef DLDPWorkModeTypeOptions {
    type enumeration {
      enum DLDP_WORK_MODE_TYPE_NORMAL {
        description "";
        value 0;
      }
      enum DLDP_WORK_MODE_TYPE_ENHANCE {
        description "";
        value 1;
      }
    }
  }
  /* hardware/dldp.proto */
  typedef DLDPNeighobrStateTypeOptions {
    type enumeration {
      enum DLDP_NEIGHBOR_STATE_TYPE_UNCONFIRM {
        description "";
        value 0;
      }
      enum DLDP_NEIGHBOR_STATE_TYPE_CONFIRM {
        description "";
        value 1;
      }
    }
  }
  /* hardware/dldp.proto */
  typedef DLDPProtocolStateTypeOptions {
    type enumeration {
      enum DLDP_PROTOCOL_STATE_TYPE_INITAL {
        description "";
        value 0;
      }
      enum DLDP_PROTOCOL_STATE_TYPE_INACTIVE {
        description "";
        value 1;
      }
      enum DLDP_PROTOCOL_STATE_TYPE_ACTIVE {
        description "";
        value 2;
      }
      enum DLDP_PROTOCOL_STATE_TYPE_ADVERTISEMENT {
        description "";
        value 3;
      }
      enum DLDP_PROTOCOL_STATE_TYPE_PROBE {
        description "";
        value 4;
      }
      enum DLDP_PROTOCOL_STATE_TYPE_DISABLE {
        description "";
        value 5;
      }
      enum DLDP_PROTOCOL_STATE_TYPE_DELAY_DOWN {
        description "";
        value 6;
      }
    }
  }
  /* hardware/hardware.proto */
  typedef PowerRedundantTypeOptions {
    type enumeration {
      enum POWER_REDUNDANT_TYPE_A {
        description "[PSU A]";
        value 0;
      }
      enum POWER_REDUNDANT_TYPE_B {
        description "[PSU B]";
        value 1;
      }
    }
  }


  /* **************************************************************************************************
   * Msgs        : 57                                                                                 *
   ************************************************************************************************** */
  /* hardware/common.proto */
  grouping IPv4Static {
    leaf IPAddress {
      type string;
    }
    leaf SubnetMask {
      type string;
    }
  }
  /* hardware/dldp.proto */
  grouping DLDPConfig {
    container System {
      uses DLDPSystemConfig;
    }
    container Port {
      uses DLDPPortConfig;
    }
  }
  /* hardware/dldp.proto */
  grouping DLDPSystemConfig {
    leaf Enabled {
      type boolean;
    }
    leaf AdvertisementInterval {
      type int32;
    }
    leaf ShutDownMode {
      type ShutdownModeTypeOptions;
    }
    leaf AuthMode {
      type DLDPAuthCationModeTypeOptions;
    }
    leaf WorkMode {
      type DLDPWorkModeTypeOptions;
    }
  }
  /* hardware/dldp.proto */
  grouping DLDPPortConfig {
    container List {
      list List_Entry {
        uses DLDPPortConfigEntry;
      }
    }
  }
  /* hardware/dldp.proto */
  grouping DLDPPortConfigEntry {
    container IdentifyNo {
      uses intri-device:InterfaceIdentify;
    }
    leaf Enabled {
      type boolean;
    }
  }
  /* hardware/dldp.proto */
  grouping DLDPPortStatus {
    container List {
      uses DLDPPortStatusEntry;
    }
  }
  /* hardware/dldp.proto */
  grouping DLDPPortStatusEntry {
    container IdentifyNo {
      uses intri-device:InterfaceIdentify;
    }
    leaf Enabled {
      type boolean;
    }
    leaf State {
      type DLDPProtocolStateTypeOptions;
    }
    leaf Link {
      type boolean;
    }
  }
  /* hardware/dldp.proto */
  grouping DLDPNeighborEntry {
    leaf NeighborMACAddress {
      type string;
    }
    leaf PortNo {
      type int32;
    }
    leaf NeighborAgetime {
      type int32;
    }
    leaf NeighborState {
      type DLDPNeighobrStateTypeOptions;
    }
  }
  /* hardware/hardware.proto */
  grouping EnableRequest {
    container List {
      list List_Entry {
        uses EnableRequestEntry;
      }
    }
  }
  /* hardware/hardware.proto */
  grouping EnableRequestEntry {
    container IdentifyNo {
      uses intri-device:InterfaceIdentify;
    }
    leaf Enabled {
      type boolean;
    }
  }
  /* hardware/hardware.proto */
  grouping PortLED {
    container List {
      list List_Entry {
        uses PortLEDEntry;
      }
    }
  }
  /* hardware/hardware.proto */
  grouping PortLEDEntry {
    container IdentifyNo {
      uses intri-device:InterfaceIdentify;
    }
    leaf State {
      type LEDBehaviorModeTypeOptions;
    }
  }
  /* hardware/hardware.proto */
  grouping BoardLED {
    leaf Power {
      type LEDBehaviorModeTypeOptions;
    }
    leaf System {
      type LEDBehaviorModeTypeOptions;
    }
    leaf PoEMax {
      type LEDBehaviorModeTypeOptions;
    }
    leaf Fan {
      type LEDBehaviorModeTypeOptions;
    }
    leaf GPS {
      type LEDBehaviorModeTypeOptions;
    }
  }
  /* hardware/hardware.proto */
  grouping LEDStatus {
    container PortLED {
      uses PortLED;
    }
    container SystemLED {
      uses BoardLED;
    }
  }
  /* hardware/hardware.proto */
  grouping Coordinates {
    leaf Latitude {
      type string;
    }
    leaf Longitude {
      type string;
    }
  }
  /* hardware/hardware.proto */
  grouping GNSSVerboseInfomation {
    leaf Mode {
      type string;
    }
    leaf NavigationalStatus {
      type string;
    }
    leaf Speed {
      type decimal64 {
        fraction-digits 2;
      }
    }
    leaf Course {
      type decimal64 {
        fraction-digits 2;
      }
    }
    leaf MagneticVariation {
      type decimal64 {
        fraction-digits 2;
      }
    }
  }
  /* hardware/hardware.proto */
  grouping GPSEnable {
    leaf Enabled {
      type boolean;
    }
  }
  /* hardware/hardware.proto */
  grouping GPSStatus {
    leaf Enabled {
      type boolean;
    }
    leaf Status {
      type GPSStatusTypeOptions;
    }
    container VerboseInfo {
      uses GNSSVerboseInfomation;
    }
    container Location {
      uses Coordinates;
    }
    container DateTime {
      uses intri-timestamp:Timestamp;
    }
  }
  /* hardware/hardware.proto */
  grouping GPSCommand {
    leaf Request {
      type string;
    }
    container Respond {
      leaf-list Respond_Entry {
        type string;
      }
    }
  }
  /* hardware/hardware.proto */
  grouping USBStatus {
    leaf Enabled {
      type boolean;
    }
    leaf Connected {
      type boolean;
    }
    leaf ConnectedDevice {
      type string;
    }
  }
  /* hardware/hardware.proto */
  grouping USBEthernetConfig {
    container Static {
      uses IPv4Static;
    }
  }
  /* hardware/hardware.proto */
  grouping FanSpeedConfig {
    container List {
      list List_Entry {
        uses FanSpeedConfigEntry;
      }
    }
  }
  /* hardware/hardware.proto */
  grouping FanSpeedConfigEntry {
    leaf FanNo {
      type int32;
    }
    leaf RotatingSpeed {
      type int32;
    }
  }
  /* hardware/hardware.proto */
  grouping FanStatus {
    container List {
      list List_Entry {
        uses FanStatusEntry;
      }
    }
  }
  /* hardware/hardware.proto */
  grouping FanStatusEntry {
    leaf FanNo {
      type int32;
    }
    leaf RotatingSpeedRPM {
      type int32;
    }
  }
  /* hardware/hardware.proto */
  grouping TemperatureStatus {
    container List {
      list List_Entry {
        uses TemperatureStatusEntry;
      }
    }
  }
  /* hardware/hardware.proto */
  grouping TemperatureStatusEntry {
    leaf Name {
      type string;
    }
    leaf ID {
      type int32;
    }
    leaf Temperature {
      type int32;
    }
  }
  /* hardware/hardware.proto */
  grouping PowerRedundantState {
    container RedundantList {
      list RedundantList_Entry {
        uses PowerRedundantStateEntry;
      }
    }
  }
  /* hardware/hardware.proto */
  grouping PowerRedundantStateEntry {
    leaf PwOption {
      type PowerRedundantTypeOptions;
    }
    leaf PowerRedundantPlugIn {
      type boolean;
    }
    leaf PowerRedundantACOk {
      type boolean;
    }
    leaf PowerRedundantOk {
      type boolean;
    }
    leaf PowerRedundantVoltage {
      type decimal64 {
        fraction-digits 2;
      }
    }
    leaf PowerRedundantCurrent {
      type decimal64 {
        fraction-digits 2;
      }
    }
    leaf PowerRedundantPowerConsumption {
      type decimal64 {
        fraction-digits 2;
      }
    }
    leaf PowerRedundantTemperature {
      type decimal64 {
        fraction-digits 2;
      }
    }
  }
  /* hardware/hardware.proto */
  grouping PowerGeneralState {
    leaf Power_12V {
      type boolean;
    }
    leaf Power_54V {
      type boolean;
    }
  }
  /* hardware/hardware.proto */
  grouping PowerState {
    leaf Type {
      type PowerTypeOptions;
    }
    choice PowerType {
      container PowerRedundantState {
        uses PowerRedundantState;
      }
      container PowerGeneralState {
        uses PowerGeneralState;
      }
    }
  }
  /* hardware/hardware.proto */
  grouping TimeControlRegister {
    leaf RegBase {
      type int32;
    }
    leaf Offset {
      type int32;
    }
    leaf Data {
      type uint8;
    }
  }
  /* hardware/monitor.proto */
  grouping Config {
    container LED {
      uses LEDConfig;
    }
    container Fan {
      uses FanSpeedConfig;
    }
    container GPS {
      uses GPSEnable;
    }
  }
  /* hardware/monitor.proto */
  grouping Ports {
    container List {
      list List_Entry {
        uses PortEntry;
      }
    }
  }
  /* hardware/monitor.proto */
  grouping PortEntry {
    container IdentifyNo {
      uses intri-device:InterfaceIdentify;
    }
    leaf HardwarePortNo {
      type int32;
    }
    leaf SwitchPortNo {
      type int32;
    }
    leaf InterfaceType {
      type intri-device:PortInterfaceTypeOptions;
    }
    container Properies {
      leaf-list Properies_Entry {
        type intri-device:PortPropertyTypeOptions;
      }
    }
    leaf SupportPoE {
      type boolean;
    }
    leaf SupportSFP {
      type boolean;
    }
    leaf LinkLED {
      type LEDBehaviorModeTypeOptions;
    }
    leaf PoELED {
      type LEDBehaviorModeTypeOptions;
    }
    leaf SpeedLED {
      type LEDBehaviorModeTypeOptions;
    }
  }
  /* hardware/monitor.proto */
  grouping SystemInfo {
    container Fan {
      uses FanPercent;
    }
    container Temp {
      uses TemperatureStatus;
    }
    container BoardLED {
      uses BoardLED;
    }
    container GPS {
      uses GPSStatus;
    }
  }
  /* hardware/monitor.proto */
  grouping LEDConfig {
    leaf Mode {
      type LEDModeTypeOptions;
    }
    leaf ResetButton {
      type boolean;
    }
  }
  /* hardware/monitor.proto */
  grouping FanPercent {
    container List {
      list List_Entry {
        uses FanPercentEntry;
      }
    }
  }
  /* hardware/monitor.proto */
  grouping FanPercentEntry {
    leaf FanNo {
      type int32;
    }
    leaf PercentRPM {
      type int32;
    }
  }
  /* hardware/monitor.proto */
  grouping LEDType {
    leaf LED {
      type LEDBehaviorModeTypeOptions;
    }
  }
  /* hardware/monitor.proto */
  grouping SignalState {
    container List {
      list List_Entry {
        uses SignalStateEntry;
      }
    }
  }
  /* hardware/monitor.proto */
  grouping SignalStateEntry {
    container IdentifyNo {
      uses intri-device:InterfaceIdentify;
    }
    leaf State {
      type boolean;
    }
  }
  /* hardware/monitor.proto */
  grouping SFPInfo {
    container List {
      list List_Entry {
        uses SFPInfoEntry;
      }
    }
  }
  /* hardware/monitor.proto */
  grouping SFPInfoEntry {
    container IdentifyNo {
      uses intri-device:InterfaceIdentify;
    }
    container Info {
      uses intri-event:SFPInfo;
    }
  }
  /* hardware/monitor.proto */
  grouping DeviceI2CAddress {
    container Bus0 {
      leaf-list Bus0_Entry {
        type string;
      }
    }
    leaf Mux {
      type string;
    }
    container List {
      list List_Entry {
        uses DeviceI2CAddressInfo;
      }
    }
  }
  /* hardware/monitor.proto */
  grouping DeviceI2CAddressInfo {
    leaf Ch {
      type int32;
    }
    container Address {
      leaf-list Address_Entry {
        type string;
      }
    }
  }
  /* hardware/monitor.proto */
  grouping InfoList {
    container Info {
      leaf-list Info_Entry {
        type string;
      }
    }
  }
  /* hardware/monitor.proto */
  grouping Enable {
    leaf Enabled {
      type boolean;
    }
  }
  /* hardware/monitor.proto */
  grouping Network {
    leaf IP {
      type string;
    }
    leaf Mask {
      type string;
    }
  }
  /* hardware/monitor.proto */
  grouping MCUInfo {
    container List {
      list List_Entry {
        uses MCUVersion;
      }
    }
  }
  /* hardware/monitor.proto */
  grouping MCUVersion {
    leaf Name {
      type string;
    }
    leaf Version {
      type string;
    }
  }
  /* hardware/poe.proto */
  grouping PoESetting {
    container List {
      list List_Entry {
        uses PoESettingEntry;
      }
    }
  }
  /* hardware/poe.proto */
  grouping PoESettingEntry {
    container IdentifyNo {
      uses intri-device:InterfaceIdentify;
    }
    leaf Enable {
      type boolean;
    }
    leaf Mode {
      type PoEPortModeTypeOptions;
    }
    leaf Priority {
      type PoEPriorityLevelTypeOptions;
    }
  }
  /* hardware/poe.proto */
  grouping PoEPortStatusList {
    container List {
      list List_Entry {
        uses PoEPortStatusEntry;
      }
    }
  }
  /* hardware/poe.proto */
  grouping PoEPortStatusEntry {
    container IdentifyNo {
      uses intri-device:InterfaceIdentify;
    }
    leaf IsEnabled {
      type boolean;
    }
    leaf IsLinkUp {
      type boolean;
    }
    leaf Class {
      type PoEDeterminedClassTypeOptions;
    }
    leaf PowerConsumption {
      type decimal64 {
        fraction-digits 2;
      }
    }
    leaf Current {
      type decimal64 {
        fraction-digits 2;
      }
    }
    leaf Voltage {
      type decimal64 {
        fraction-digits 2;
      }
    }
    leaf Temperature {
      type decimal64 {
        fraction-digits 2;
      }
    }
    leaf Condition {
      type PoEConditionTypeOptions;
    }
  }
  /* hardware/poe.proto */
  grouping PoESystemStatus {
    leaf MinShutDownVoltage {
      type decimal64 {
        fraction-digits 2;
      }
    }
    leaf MaxShutDownVoltage {
      type decimal64 {
        fraction-digits 2;
      }
    }
    leaf VMainVoltage {
      type decimal64 {
        fraction-digits 2;
      }
    }
    leaf IMainCurrent {
      type decimal64 {
        fraction-digits 2;
      }
    }
    leaf PowerConsumption {
      type decimal64 {
        fraction-digits 2;
      }
    }
    leaf Budget {
      type int32;
    }
    leaf Version {
      type string;
    }
  }
  /* hardware/poe.proto */
  grouping PoESystemBudgetEntry {
    leaf Budget {
      type int32;
    }
  }


  /* **************************************************************************************************
   * Services    : 2                                                                                  *
   ************************************************************************************************** */

  /* **************************************************************************************************
   * Service     : Hardware                                                                           *
   * Methods     : 54                                                                                 *
   ************************************************************************************************** */
  /* hardware/service.proto */
  rpc intri-hardware-GetSFPPlugin {
    input  {
      uses intri-device:PortList;
    }
    output  {
      uses SignalState;
    }
  }
  /* hardware/service.proto */
  rpc intri-hardware-GetSFPRxLoss {
    input  {
      uses intri-device:PortList;
    }
    output  {
      uses SignalState;
    }
  }
  /* hardware/service.proto */
  rpc intri-hardware-GetSFPTxFaild {
    input  {
      uses intri-device:PortList;
    }
    output  {
      uses SignalState;
    }
  }
  /* hardware/service.proto */
  rpc intri-hardware-GetSFPRom {
    input  {
      uses intri-device:PortList;
    }
    output  {
      uses SFPInfo;
    }
  }
  /* hardware/service.proto */
  rpc intri-hardware-GetSFPTxDisable {
    input  {
      uses intri-device:PortList;
    }
    output  {
      uses SignalState;
    }
  }
  /* hardware/service.proto */
  rpc intri-hardware-SetSFPTxDisable {
    input  {
      uses EnableRequest;
    }
  }
  /* hardware/service.proto */
  rpc intri-hardware-GetSFPLED {
    input  {
      uses intri-device:PortList;
    }
    output  {
      uses PortLED;
    }
  }
  /* hardware/service.proto */
  rpc intri-hardware-SetSFPLED {
    input  {
      uses PortLED;
    }
  }
  /* hardware/service.proto */
  rpc intri-hardware-GetResetButtonStatus {
    output  {
      uses intri-common:State;
    }
  }
  /* hardware/service.proto */
  rpc intri-hardware-GetConfig {
    output  {
      uses Config;
    }
  }
  /* hardware/service.proto */
  rpc intri-hardware-SetConfig {
    input  {
      uses Config;
    }
  }
  /* hardware/service.proto */
  rpc intri-hardware-GetPortInfo {
    output  {
      uses Ports;
    }
  }
  /* hardware/service.proto */
  rpc intri-hardware-GetTemperature {
    output  {
      uses TemperatureStatus;
    }
  }
  /* hardware/service.proto */
  rpc intri-hardware-GetPowerStatus {
    output  {
      uses PowerState;
    }
  }
  /* hardware/service.proto */
  rpc intri-hardware-GetGPS {
    output  {
      uses GPSStatus;
    }
  }
  /* hardware/service.proto */
  rpc intri-hardware-SetGPS {
    input  {
      uses Enable;
    }
  }
  /* hardware/service.proto */
  rpc intri-hardware-SetGPSCommand {
    input  {
      uses GPSCommand;
    }
    output  {
      uses GPSCommand;
    }
  }
  /* hardware/service.proto */
  rpc intri-hardware-GetSystemLED {
    output  {
      uses LEDType;
    }
  }
  /* hardware/service.proto */
  rpc intri-hardware-SetSystemLED {
    input  {
      uses LEDType;
    }
  }
  /* hardware/service.proto */
  rpc intri-hardware-SetFanSpeed {
    input  {
      uses FanPercent;
    }
  }
  /* hardware/service.proto */
  rpc intri-hardware-GetFanSpeed {
    output  {
      uses FanPercent;
    }
  }
  /* hardware/service.proto */
  rpc intri-hardware-SetGPSLED {
    input  {
      uses LEDType;
    }
  }
  /* hardware/service.proto */
  rpc intri-hardware-GetGPSLED {
    output  {
      uses LEDType;
    }
  }
  /* hardware/service.proto */
  rpc intri-hardware-SetFanLED {
    input  {
      uses LEDType;
    }
  }
  /* hardware/service.proto */
  rpc intri-hardware-GetFanLED {
    output  {
      uses LEDType;
    }
  }
  /* hardware/service.proto */
  rpc intri-hardware-SetUSBEnable {
    input  {
      uses Enable;
    }
  }
  /* hardware/service.proto */
  rpc intri-hardware-GetUSBStatus {
    output  {
      uses USBStatus;
    }
  }
  /* hardware/service.proto */
  rpc intri-hardware-SetHeater {
    input  {
      uses Enable;
    }
  }
  /* hardware/service.proto */
  rpc intri-hardware-GetHeater {
    input  {
      uses Enable;
    }
  }
  /* hardware/service.proto */
  rpc intri-hardware-GetMCUVersion {
    output  {
      uses MCUInfo;
    }
  }
  /* hardware/service.proto */
  rpc intri-hardware-GetI2CDevice {
    output  {
      uses DeviceI2CAddress;
    }
  }
  /* hardware/service.proto */
  rpc intri-hardware-GetCPU {
    output  {
      uses InfoList;
    }
  }
  /* hardware/service.proto */
  rpc intri-hardware-GetMemoryTotal {
    output  {
      uses InfoList;
    }
  }
  /* hardware/service.proto */
  rpc intri-hardware-RunMemoryTest {
    output  {
      uses InfoList;
    }
  }
  /* hardware/service.proto */
  rpc intri-hardware-GetECCState {
    output  {
      uses InfoList;
    }
  }
  /* hardware/service.proto */
  rpc intri-hardware-GetSPI {
    output  {
      uses InfoList;
    }
  }
  /* hardware/service.proto */
  rpc intri-hardware-GetSPIPartition {
    output  {
      uses InfoList;
    }
  }
  /* hardware/service.proto */
  rpc intri-hardware-GetSPIFlash {
    output  {
      uses InfoList;
    }
  }
  /* hardware/service.proto */
  rpc intri-hardware-GeteMMC {
    output  {
      uses InfoList;
    }
  }
  /* hardware/service.proto */
  rpc intri-hardware-GeteMMCPartition {
    output  {
      uses InfoList;
    }
  }
  /* hardware/service.proto */
  rpc intri-hardware-SetWatchDog {
    input  {
      uses Enable;
    }
  }
  /* hardware/service.proto */
  rpc intri-hardware-GetSecureICExist {
    output  {
      uses InfoList;
    }
  }
  /* hardware/service.proto */
  rpc intri-hardware-RunSecureICVerify {
    output  {
      uses InfoList;
    }
  }
  /* hardware/service.proto */
  rpc intri-hardware-GetRTC {
    output  {
      uses intri-timestamp:Timestamp;
    }
  }
  /* hardware/service.proto */
  rpc intri-hardware-SetRTC {
    input  {
      uses intri-timestamp:Timestamp;
    }
  }
  /* hardware/service.proto */
  rpc intri-hardware-RunSync {
  }
  /* hardware/service.proto */
  rpc intri-hardware-SetNetwork {
    input  {
      uses Network;
    }
  }
  /* hardware/service.proto */
  rpc intri-hardware-GetNetwork {
    output  {
      uses Network;
    }
  }
  /* hardware/service.proto */
  rpc intri-hardware-SetUSBNetwork {
    input  {
      uses USBEthernetConfig;
    }
  }
  /* hardware/service.proto */
  rpc intri-hardware-GetUSBNetwork {
    output  {
      uses USBEthernetConfig;
    }
  }
  /* hardware/service.proto */
  rpc intri-hardware-RunPing {
    input  {
      uses Network;
    }
    output  {
      uses InfoList;
    }
  }
  /* hardware/service.proto */
  rpc intri-hardware-RunProdMode {
  }
  /* hardware/service.proto */
  rpc intri-hardware-GetTimeControlRegister {
    input  {
      uses TimeControlRegister;
    }
    output  {
      uses TimeControlRegister;
    }
  }
  /* hardware/service.proto */
  rpc intri-hardware-SetTimeControlRegister {
    input  {
      uses TimeControlRegister;
    }
  }

  /* **************************************************************************************************
   * Service     : HardwarePoE                                                                        *
   * Methods     : 9                                                                                  *
   ************************************************************************************************** */
  /* hardware/service.proto */
  rpc intri-hardware-SetSystemBudget {
    input  {
      uses PoESystemBudgetEntry;
    }
  }
  /* hardware/service.proto */
  rpc intri-hardware-SetPortSetting {
    input  {
      uses PoESetting;
    }
  }
  /* hardware/service.proto */
  rpc intri-hardware-GetPortSetting {
    output  {
      uses PoESetting;
    }
  }
  /* hardware/service.proto */
  rpc intri-hardware-GetSystemStatus {
    output  {
      uses PoESystemStatus;
    }
  }
  /* hardware/service.proto */
  rpc intri-hardware-GetPortStatus {
    output  {
      uses PoEPortStatusList;
    }
  }
  /* hardware/service.proto */
  rpc intri-hardware-SetPortLED {
    input  {
      uses PortLED;
    }
  }
  /* hardware/service.proto */
  rpc intri-hardware-GetPortLED {
    output  {
      uses PortLED;
    }
  }
  /* hardware/service.proto */
  rpc intri-hardware-GetPoEMaxLED {
    output  {
      uses LEDType;
    }
  }
  /* hardware/service.proto */
  rpc intri-hardware-SetPoEMaxLED {
    input  {
      uses LEDType;
    }
  }

}
