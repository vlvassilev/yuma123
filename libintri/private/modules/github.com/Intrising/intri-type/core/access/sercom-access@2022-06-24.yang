module sercom-access {

  namespace "sercom:sercom-access";
  prefix "sercom-access";
  organization "
    Sercomm Inc.";
  contact "
    sercomm@sercomm.com.tw";
  revision 2022-06-24 {
    description "Build date.";
  }

  import sercom-event {
    prefix sercom-event;
  }
  import sercom-empty {
    prefix sercom-empty;
  }
  import sercom-common {
    prefix sercom-common;
  }
  typedef AuthenticationModeTypeOptions {
    type enumeration {
      enum AUTHENTICATION_MODE_TYPE_LOCAL {
        description "[Local] Verify against local database";
        value 0;
      }
      enum AUTHENTICATION_MODE_TYPE_LOCAL_THEN_RADIUS {
        description "[Local Then RADIUS] Verify against local database then try RADIUS server if user is not locally defined";
        value 1;
      }
      enum AUTHENTICATION_MODE_TYPE_RADIUS {
        description "[RADIUS] Verify against RADIUS server";
        value 2;
      }
      enum AUTHENTICATION_MODE_TYPE_LOCAL_THEN_TACACS {
        description "[Local Then TACACS+] Verify against local database then try TACACS+ server if user is not locally defined";
        value 3;
      }
      enum AUTHENTICATION_MODE_TYPE_TACACS {
        description "[TACACS+] Verify against TACACS+ server";
        value 4;
      }
      enum AUTHENTICATION_MODE_TYPE_RADIUS_THEN_LOCAL {
        description "[RADIUS Then Local] Verify against RADIUS server then try local database";
        value 5;
      }
      enum AUTHENTICATION_MODE_TYPE_TACACS_THEN_LOCAL {
        description "[TACACS+ Then Local] Verify against TACACS+ server then try local database";
        value 6;
      }
    }
  }
  typedef AuthenticationServerTypeOptions {
    type enumeration {
      enum AUTHENTICATION_SERVER_TYPE_RADIUS {
        description "[RADIUS]";
        value 0;
      }
      enum AUTHENTICATION_SERVER_TYPE_TACACS {
        description "[TACACS+]";
        value 1;
      }
    }
  }
  typedef RestrictionModeTypeOptions {
    type enumeration {
      enum RESTRICTION_MODE_TYPE_UNUSED {
        description "[Unused]";
        value 0;
      }
      enum RESTRICTION_MODE_TYPE_PERMIT {
        description "[Permit]";
        value 1;
      }
      enum RESTRICTION_MODE_TYPE_DENY {
        description "[Deny]";
        value 2;
      }
    }
  }
  typedef RightsTypeOptions {
    type enumeration {
      enum RIGHTS_TYPE_NO_ACCESS {
        description "[No Access]";
        value 0;
      }
      enum RIGHTS_TYPE_EXECUTE_ONLY {
        description "[Execute Only]";
        value 1;
      }
      enum RIGHTS_TYPE_READ_ONLY {
        description "[Read Only]";
        value 2;
      }
      enum RIGHTS_TYPE_READ_WRITE {
        description "[Read Write]";
        value 3;
      }
      enum RIGHTS_TYPE_READ_EXECUTE {
        description "[Read Execute]";
        value 4;
      }
      enum RIGHTS_TYPE_READ_WRITE_EXECUTE {
        description "[Read Write Execute]";
        value 5;
      }
    }
  }
  typedef UserEntrySNMPV3SecurityLevelTypeOptions {
    type enumeration {
      enum USER_ENTRY_SNMP_V3_SECURITY_LEVEL_TYPE_NO_AUTH_NO_PRIV {
        description "[None]";
        value 0;
      }
      enum USER_ENTRY_SNMP_V3_SECURITY_LEVEL_TYPE_AUTH_NO_PRIV {
        description "[Only Auth]";
        value 1;
      }
      enum USER_ENTRY_SNMP_V3_SECURITY_LEVEL_TYPE_AUTH_PRIV {
        description "[Auth & Privacy]";
        value 2;
      }
    }
  }
  typedef UserEntrySNMPV3AuthAlgorithmTypeOptions {
    type enumeration {
      enum USER_ENTRY_SNMP_V3_AUTH_ALGORITHM_TYPE_NO_AUTHENTICATION {
        description "[None]";
        value 0;
      }
      enum USER_ENTRY_SNMP_V3_AUTH_ALGORITHM_TYPE_MD5 {
        description "[MD5]";
        value 1;
      }
      enum USER_ENTRY_SNMP_V3_AUTH_ALGORITHM_TYPE_SHA_1 {
        description "[SHA 1]";
        value 2;
      }
      enum USER_ENTRY_SNMP_V3_AUTH_ALGORITHM_TYPE_SHA_256 {
        description "[SHA 256]";
        value 3;
      }
    }
  }
  typedef UserEntrySNMPV3PrivacyAlgorithmTypeOptions {
    type enumeration {
      enum USER_ENTRY_SNMP_V3_PRIVACY_ALGORITHM_TYPE_NO_PRIVACY {
        description "[None]";
        value 0;
      }
      enum USER_ENTRY_SNMP_V3_PRIVACY_ALGORITHM_TYPE_DES {
        description "[DES]";
        value 1;
      }
      enum USER_ENTRY_SNMP_V3_PRIVACY_ALGORITHM_TYPE_AES {
        description "[AES]";
        value 2;
      }
      enum USER_ENTRY_SNMP_V3_PRIVACY_ALGORITHM_TYPE_AES_192 {
        description "[AES 192]";
        value 3;
      }
      enum USER_ENTRY_SNMP_V3_PRIVACY_ALGORITHM_TYPE_AES_256 {
        description "[AES 256]";
        value 4;
      }
    }
  }
  grouping AuthenticationMode {
    leaf Mode {
      mandatory "true";
      type AuthenticationModeTypeOptions;
    }
  }
  grouping AuthenticationConfig {
    leaf Mode {
      mandatory "true";
      type AuthenticationModeTypeOptions;
    }
    container RADIUS {
      uses AuthenticationRADIUS;
    }
    container TACACS {
      uses AuthenticationTACACS;
    }
  }
  grouping AuthenticationTACACS {
    leaf PrimaryAuthServerName {
      mandatory "true";
      type string;
    }
    leaf FallbackAuthServerName {
      mandatory "true";
      type string;
    }
    leaf UserPrivilegeLevel0 {
      mandatory "true";
      type string;
    }
    leaf UserPrivilegeLevel1 {
      mandatory "true";
      type string;
    }
    leaf UserPrivilegeLevel15 {
      mandatory "true";
      type string;
    }
  }
  grouping AuthenticationRADIUS {
    leaf PrimaryAuthServerName {
      mandatory "true";
      type string;
    }
    leaf FallbackAuthServerName {
      mandatory "true";
      type string;
    }
    leaf UserPrivilegeLevel6 {
      mandatory "true";
      type string;
    }
    leaf UserPrivilegeLevel7 {
      mandatory "true";
      type string;
    }
  }
  grouping AuthenticationServerEntry {
    leaf Name {
      mandatory "true";
      type string;
    }
    leaf ServerType {
      mandatory "true";
      type AuthenticationServerTypeOptions;
    }
    leaf HostAddress {
      mandatory "true";
      type string;
    }
    leaf PortNumber {
      mandatory "true";
      type int32;
    }
    leaf SharedSecret {
      mandatory "true";
      type string;
    }
    leaf InterimInterval {
      mandatory "true";
      type int64;
    }
  }
  grouping AuthenticationServersConfig {
    container List {
      list List_Entry {
        uses AuthenticationServerEntry;
      }
    }
  }
  grouping LoginRequest {
    leaf Account {
      mandatory "true";
      type string;
    }
    leaf Password {
      mandatory "true";
      type string;
    }
  }
  grouping RestrictionEntry {
    leaf Name {
      mandatory "true";
      type string;
    }
    leaf Mode {
      mandatory "true";
      type RestrictionModeTypeOptions;
    }
    leaf IPAddress {
      mandatory "true";
      type string;
    }
  }
  grouping RestrictionsConfig {
    container List {
      list List_Entry {
        uses RestrictionEntry;
      }
    }
  }
  grouping UserEntry {
    leaf Name {
      mandatory "true";
      type string;
    }
    container AssociatedGroups {
      leaf-list AssociatedGroups_Entry {
        type string;
      }
    }
    leaf GeneralAccessRights {
      mandatory "true";
      type RightsTypeOptions;
    }
    leaf TelnetAccessEnabled {
      mandatory "true";
      type boolean;
    }
    leaf SSHAccessEnabled {
      mandatory "true";
      type boolean;
    }
    leaf WebAccessEnabled {
      mandatory "true";
      type boolean;
    }
    leaf SNMPAccessEnabled {
      mandatory "true";
      type boolean;
    }
    leaf EncryptedAuthPassword {
      mandatory "true";
      type string;
    }
    leaf SNMPV3SecurityLevel {
      mandatory "true";
      type UserEntrySNMPV3SecurityLevelTypeOptions;
    }
    leaf SNMPV3AuthAlgorithm {
      mandatory "true";
      type UserEntrySNMPV3AuthAlgorithmTypeOptions;
    }
    leaf SNMPV3PrivacyAlgorithm {
      mandatory "true";
      type UserEntrySNMPV3PrivacyAlgorithmTypeOptions;
    }
    leaf EncryptedSNMPAuthPassword {
      mandatory "true";
      type string;
    }
    leaf EncryptedSNMPPrivacyPassword {
      mandatory "true";
      type string;
    }
  }
  grouping PatternEntry {
    leaf Path {
      mandatory "true";
      type string;
    }
    leaf AccessRight {
      mandatory "true";
      type RightsTypeOptions;
    }
  }
  grouping UsersConfig {
    container List {
      list List_Entry {
        uses UserEntry;
      }
    }
  }
  grouping GroupEntry {
    leaf Name {
      mandatory "true";
      type string;
    }
    container Patterns {
      list Patterns_Entry {
        uses PatternEntry;
      }
    }
  }
  grouping GroupsConfig {
    container List {
      list List_Entry {
        uses GroupEntry;
      }
    }
  }
  grouping Config {
    container Authentication {
      uses AuthenticationConfig;
    }
    container Users {
      uses UsersConfig;
    }
    container Groups {
      uses GroupsConfig;
    }
    container Restrictions {
      uses RestrictionsConfig;
    }
    container Servers {
      uses AuthenticationServersConfig;
    }
  }
  grouping Password {
    leaf Password {
      mandatory "true";
      type string;
    }
    leaf Irreversable {
      mandatory "true";
      type boolean;
    }
  }
  grouping EncryptedPassword {
    leaf EncryptedPassword {
      mandatory "true";
      type string;
    }
  }
  grouping UserPasswordEntry {
    leaf Username {
      mandatory "true";
      type string;
    }
    leaf Password {
      mandatory "true";
      type string;
    }
  }
  grouping UserPassword {
    container List {
      list List_Entry {
        uses UserPasswordEntry;
      }
    }
  }
  grouping NumberOfLogins {
    leaf NumberOfLogins {
      mandatory "true";
      type int32;
    }
  }
  grouping LoginStatusEntry {
    leaf State {
      mandatory "true";
      type string;
    }
    leaf Username {
      mandatory "true";
      type string;
    }
    leaf AuthName {
      mandatory "true";
      type string;
    }
    leaf LoginID {
      mandatory "true";
      type string;
    }
    leaf LoginTimeStamp {
      mandatory "true";
      type string;
    }
    leaf LoginEpoch {
      mandatory "true";
      type string;
    }
    leaf ConnectTime {
      mandatory "true";
      type int64;
    }
    leaf Service {
      mandatory "true";
      type sercom-event:LoginInterfaceNameTypeOptions;
    }
  }
  grouping LoginStatus {
    container List {
      list List_Entry {
        uses LoginStatusEntry;
      }
    }
  }
  grouping Token {
    leaf Token {
      mandatory "true";
      type string;
    }
  }
  rpc sercom-access-Access-GetConfig {
    output {
      uses Config;
    }
  }
  rpc sercom-access-Access-GetAuthenticationConfig {
    output {
      uses AuthenticationConfig;
    }
  }
  rpc sercom-access-Access-SetAuthenticationConfig {
    input {
      uses AuthenticationConfig;
    }
  }
  rpc sercom-access-Access-Login {
    input {
      uses LoginRequest;
    }
    output {
      uses Token;
    }
  }
  rpc sercom-access-Access-Logout {
  }
  rpc sercom-access-Access-PAMLogin {
    input {
      uses LoginRequest;
    }
    output {
      uses sercom-event:LoginParameter;
    }
  }
  rpc sercom-access-Access-GetUsers {
    output {
      uses UsersConfig;
    }
  }
  rpc sercom-access-Access-AddUser {
    input {
      uses UserEntry;
    }
  }
  rpc sercom-access-Access-DeleteUser {
    input {
      uses sercom-common:Name;
    }
  }
  rpc sercom-access-Access-UpdateUser {
    input {
      uses UserEntry;
    }
  }
  rpc sercom-access-Access-RunEncryptPassword {
    input {
      uses Password;
    }
    output {
      uses EncryptedPassword;
    }
  }
  rpc sercom-access-Access-RunUserEnterPassword {
    input {
      uses UserPassword;
    }
  }
  rpc sercom-access-Access-RunUserEnterSNMPV3AuthPassword {
    input {
      uses UserPassword;
    }
  }
  rpc sercom-access-Access-RunUserEnterSNMPV3PrivacyPassword {
    input {
      uses UserPassword;
    }
  }
  rpc sercom-access-Access-GetGroups {
    output {
      uses GroupsConfig;
    }
  }
  rpc sercom-access-Access-AddGroup {
    input {
      uses GroupEntry;
    }
  }
  rpc sercom-access-Access-DeleteGroup {
    input {
      uses sercom-common:Name;
    }
  }
  rpc sercom-access-Access-UpdateGroup {
    input {
      uses GroupEntry;
    }
  }
  rpc sercom-access-Access-GetAuthenticatorServerConfig {
    output {
      uses AuthenticationServersConfig;
    }
  }
  rpc sercom-access-Access-AddAuthenticatorServerConfig {
    input {
      uses AuthenticationServerEntry;
    }
  }
  rpc sercom-access-Access-DeleteAuthenticatorServerConfig {
    input {
      uses sercom-common:Name;
    }
  }
  rpc sercom-access-Access-UpdateAuthenticatorServerConfig {
    input {
      uses AuthenticationServerEntry;
    }
  }
  rpc sercom-access-Access-GetRestrictions {
    output {
      uses RestrictionsConfig;
    }
  }
  rpc sercom-access-Access-AddRestriction {
    input {
      uses RestrictionEntry;
    }
  }
  rpc sercom-access-Access-DeleteRestriction {
    input {
      uses sercom-common:Name;
    }
  }
  rpc sercom-access-Access-UpdateRestriction {
    input {
      uses RestrictionEntry;
    }
  }
}
