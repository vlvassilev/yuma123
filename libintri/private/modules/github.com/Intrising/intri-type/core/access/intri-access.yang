// Code generated by protoc-gen-yang. DO NOT EDIT.


/* ****************************************************************************************************
 * Import Path : "github.com/Intrising/intri-type/core/access"                                        *
 * Dir Path    : github.com/Intrising/intri-type/core/access                                          *
 * Go Package  : access                                                                               *
 * Files       : 8                                                                                    *
 **************************************************************************************************** */
module intri-access {

  namespace "intri:intri-access";

  prefix "intri-access";

  organization "Intrising Inc.";

  contact "intrising@intrising.com.tw";

  revision 2022-06-23 {
    description "Build date.";
  }

  import intri-event {
    prefix intri-event;
  }
  import intri-empty {
    prefix intri-empty;
  }
  import intri-common {
    prefix intri-common;
  }


  /* **************************************************************************************************
   * Enums       : 7                                                                                  *
   ************************************************************************************************** */
  /* core/access/authentication.proto */
  typedef AuthenticationModeTypeOptions {
    type enumeration {
      enum AUTHENTICATION_MODE_TYPE_LOCAL {
        description "[Local] Verify against local database";
        value 0;
      }
      enum AUTHENTICATION_MODE_TYPE_LOCAL_THEN_RADIUS {
        description "[Local Then RADIUS] Verify against local database then try RADIUS server if user is not locally defined";
        value 1;
      }
      enum AUTHENTICATION_MODE_TYPE_RADIUS {
        description "[RADIUS] Verify against RADIUS server";
        value 2;
      }
      enum AUTHENTICATION_MODE_TYPE_LOCAL_THEN_TACACS {
        description "[Local Then TACACS+] Verify against local database then try TACACS+ server if user is not locally defined";
        value 3;
      }
      enum AUTHENTICATION_MODE_TYPE_TACACS {
        description "[TACACS+] Verify against TACACS+ server";
        value 4;
      }
      enum AUTHENTICATION_MODE_TYPE_RADIUS_THEN_LOCAL {
        description "[RADIUS Then Local] Verify against RADIUS server then try local database";
        value 5;
      }
      enum AUTHENTICATION_MODE_TYPE_TACACS_THEN_LOCAL {
        description "[TACACS+ Then Local] Verify against TACACS+ server then try local database";
        value 6;
      }
    }
  }
  /* core/access/authserver.proto */
  typedef AuthenticationServerTypeOptions {
    type enumeration {
      enum AUTHENTICATION_SERVER_TYPE_RADIUS {
        description "[RADIUS]";
        value 0;
      }
      enum AUTHENTICATION_SERVER_TYPE_TACACS {
        description "[TACACS+]";
        value 1;
      }
    }
  }
  /* core/access/restriction.proto */
  typedef RestrictionModeTypeOptions {
    type enumeration {
      enum RESTRICTION_MODE_TYPE_UNUSED {
        description "[Unused]";
        value 0;
      }
      enum RESTRICTION_MODE_TYPE_PERMIT {
        description "[Permit]";
        value 1;
      }
      enum RESTRICTION_MODE_TYPE_DENY {
        description "[Deny]";
        value 2;
      }
    }
  }
  /* core/access/user.proto */
  typedef RightsTypeOptions {
    type enumeration {
      enum RIGHTS_TYPE_NO_ACCESS {
        description "[No Access]";
        value 0;
      }
      enum RIGHTS_TYPE_EXECUTE_ONLY {
        description "[Execute Only]";
        value 1;
      }
      enum RIGHTS_TYPE_READ_ONLY {
        description "[Read Only]";
        value 2;
      }
      enum RIGHTS_TYPE_READ_WRITE {
        description "[Read Write]";
        value 3;
      }
      enum RIGHTS_TYPE_READ_EXECUTE {
        description "[Read Execute]";
        value 4;
      }
      enum RIGHTS_TYPE_READ_WRITE_EXECUTE {
        description "[Read Write Execute]";
        value 5;
      }
    }
  }
  /* core/access/user.proto */
  typedef UserEntrySNMPV3SecurityLevelTypeOptions {
    type enumeration {
      enum USER_ENTRY_SNMP_V3_SECURITY_LEVEL_TYPE_NO_AUTH_NO_PRIV {
        description "[None]";
        value 0;
      }
      enum USER_ENTRY_SNMP_V3_SECURITY_LEVEL_TYPE_AUTH_NO_PRIV {
        description "[Only Auth]";
        value 1;
      }
      enum USER_ENTRY_SNMP_V3_SECURITY_LEVEL_TYPE_AUTH_PRIV {
        description "[Auth & Privacy]";
        value 2;
      }
    }
  }
  /* core/access/user.proto */
  typedef UserEntrySNMPV3AuthAlgorithmTypeOptions {
    type enumeration {
      enum USER_ENTRY_SNMP_V3_AUTH_ALGORITHM_TYPE_NO_AUTHENTICATION {
        description "[None]";
        value 0;
      }
      enum USER_ENTRY_SNMP_V3_AUTH_ALGORITHM_TYPE_MD5 {
        description "[MD5]";
        value 1;
      }
      enum USER_ENTRY_SNMP_V3_AUTH_ALGORITHM_TYPE_SHA_1 {
        description "[SHA 1]";
        value 2;
      }
      enum USER_ENTRY_SNMP_V3_AUTH_ALGORITHM_TYPE_SHA_256 {
        description "[SHA 256]";
        value 3;
      }
    }
  }
  /* core/access/user.proto */
  typedef UserEntrySNMPV3PrivacyAlgorithmTypeOptions {
    type enumeration {
      enum USER_ENTRY_SNMP_V3_PRIVACY_ALGORITHM_TYPE_NO_PRIVACY {
        description "[None]";
        value 0;
      }
      enum USER_ENTRY_SNMP_V3_PRIVACY_ALGORITHM_TYPE_DES {
        description "[DES]";
        value 1;
      }
      enum USER_ENTRY_SNMP_V3_PRIVACY_ALGORITHM_TYPE_AES {
        description "[AES]";
        value 2;
      }
      enum USER_ENTRY_SNMP_V3_PRIVACY_ALGORITHM_TYPE_AES_192 {
        description "[AES 192]";
        value 3;
      }
      enum USER_ENTRY_SNMP_V3_PRIVACY_ALGORITHM_TYPE_AES_256 {
        description "[AES 256]";
        value 4;
      }
    }
  }


  /* **************************************************************************************************
   * Msgs        : 23                                                                                 *
   ************************************************************************************************** */
  /* core/access/authentication.proto */
  grouping AuthenticationMode {
    leaf Mode {
      type AuthenticationModeTypeOptions;
    }
  }
  /* core/access/authentication.proto */
  grouping AuthenticationConfig {
    leaf Mode {
      type AuthenticationModeTypeOptions;
    }
    container RADIUS {
      uses AuthenticationRADIUS;
    }
    container TACACS {
      uses AuthenticationTACACS;
    }
  }
  /* core/access/authentication.proto */
  grouping AuthenticationTACACS {
    leaf PrimaryAuthServerName {
      type string;
    }
    leaf FallbackAuthServerName {
      type string;
    }
    leaf UserPrivilegeLevel0 {
      type string;
    }
    leaf UserPrivilegeLevel1 {
      type string;
    }
    leaf UserPrivilegeLevel15 {
      type string;
    }
  }
  /* core/access/authentication.proto */
  grouping AuthenticationRADIUS {
    leaf PrimaryAuthServerName {
      type string;
    }
    leaf FallbackAuthServerName {
      type string;
    }
    leaf UserPrivilegeLevel6 {
      type string;
    }
    leaf UserPrivilegeLevel7 {
      type string;
    }
  }
  /* core/access/authserver.proto */
  grouping AuthenticationServerEntry {
    leaf Name {
      type string;
    }
    leaf ServerType {
      type AuthenticationServerTypeOptions;
    }
    leaf HostAddress {
      type string;
    }
    leaf PortNumber {
      type int32;
    }
    leaf SharedSecret {
      type string;
    }
    leaf InterimInterval {
      type int64;
    }
  }
  /* core/access/authserver.proto */
  grouping AuthenticationServersConfig {
    container List {
      list List_Entry {
        uses AuthenticationServerEntry;
      }
    }
  }
  /* core/access/login.proto */
  grouping LoginRequest {
    leaf Account {
      type string;
    }
    leaf Password {
      type string;
    }
  }
  /* core/access/restriction.proto */
  grouping RestrictionEntry {
    leaf Name {
      type string;
    }
    leaf Mode {
      type RestrictionModeTypeOptions;
    }
    leaf IPAddress {
      type string;
    }
  }
  /* core/access/restriction.proto */
  grouping RestrictionsConfig {
    container List {
      list List_Entry {
        uses RestrictionEntry;
      }
    }
  }
  /* core/access/user.proto */
  grouping UserEntry {
    leaf Name {
      type string;
    }
    container AssociatedGroups {
      leaf-list AssociatedGroups_Entry {
        type string;
      }
    }
    leaf GeneralAccessRights {
      type RightsTypeOptions;
    }
    leaf TelnetAccessEnabled {
      type boolean;
    }
    leaf SSHAccessEnabled {
      type boolean;
    }
    leaf WebAccessEnabled {
      type boolean;
    }
    leaf SNMPAccessEnabled {
      type boolean;
    }
    leaf EncryptedAuthPassword {
      type string;
    }
    leaf SNMPV3SecurityLevel {
      type UserEntrySNMPV3SecurityLevelTypeOptions;
    }
    leaf SNMPV3AuthAlgorithm {
      type UserEntrySNMPV3AuthAlgorithmTypeOptions;
    }
    leaf SNMPV3PrivacyAlgorithm {
      type UserEntrySNMPV3PrivacyAlgorithmTypeOptions;
    }
    leaf EncryptedSNMPAuthPassword {
      type string;
    }
    leaf EncryptedSNMPPrivacyPassword {
      type string;
    }
  }
  /* core/access/user.proto */
  grouping PatternEntry {
    leaf Path {
      type string;
    }
    leaf AccessRight {
      type RightsTypeOptions;
    }
  }
  /* core/access/user.proto */
  grouping UsersConfig {
    container List {
      list List_Entry {
        uses UserEntry;
      }
    }
  }
  /* core/access/user.proto */
  grouping GroupEntry {
    leaf Name {
      type string;
    }
    container Patterns {
      list Patterns_Entry {
        uses PatternEntry;
      }
    }
  }
  /* core/access/user.proto */
  grouping GroupsConfig {
    container List {
      list List_Entry {
        uses GroupEntry;
      }
    }
  }
  /* core/access/access.proto */
  grouping Config {
    container Authentication {
      uses AuthenticationConfig;
    }
    container Users {
      uses UsersConfig;
    }
    container Groups {
      uses GroupsConfig;
    }
    container Restrictions {
      uses RestrictionsConfig;
    }
    container Servers {
      uses AuthenticationServersConfig;
    }
  }
  /* core/access/access.proto */
  grouping Password {
    leaf Password {
      type string;
    }
    leaf Irreversable {
      type boolean;
    }
  }
  /* core/access/access.proto */
  grouping EncryptedPassword {
    leaf EncryptedPassword {
      type string;
    }
  }
  /* core/access/access.proto */
  grouping UserPasswordEntry {
    leaf Username {
      type string;
    }
    leaf Password {
      type string;
    }
  }
  /* core/access/access.proto */
  grouping UserPassword {
    container List {
      list List_Entry {
        uses UserPasswordEntry;
      }
    }
  }
  /* core/access/access.proto */
  grouping NumberOfLogins {
    leaf NumberOfLogins {
      type int32;
    }
  }
  /* core/access/access.proto */
  grouping LoginStatusEntry {
    leaf State {
      type string;
    }
    leaf Username {
      type string;
    }
    leaf AuthName {
      type string;
    }
    leaf LoginID {
      type string;
    }
    leaf LoginTimeStamp {
      type string;
    }
    leaf LoginEpoch {
      type string;
    }
    leaf ConnectTime {
      type int64;
    }
    leaf Service {
      type intri-event:LoginInterfaceNameTypeOptions;
    }
  }
  /* core/access/access.proto */
  grouping LoginStatus {
    container List {
      list List_Entry {
        uses LoginStatusEntry;
      }
    }
  }
  /* core/access/access.proto */
  grouping Token {
    leaf Token {
      type string;
    }
  }


  /* **************************************************************************************************
   * Services    : 1                                                                                  *
   ************************************************************************************************** */

  /* **************************************************************************************************
   * Service     : Access                                                                             *
   * Methods     : 26                                                                                 *
   ************************************************************************************************** */
  /* core/access/service.proto */
  rpc intri-access-GetConfig {
    output  {
      uses Config;
    }
  }
  /* core/access/service.proto */
  rpc intri-access-GetAuthenticationConfig {
    output  {
      uses AuthenticationConfig;
    }
  }
  /* core/access/service.proto */
  rpc intri-access-SetAuthenticationConfig {
    input  {
      uses AuthenticationConfig;
    }
  }
  /* core/access/service.proto */
  rpc intri-access-Login {
    input  {
      uses LoginRequest;
    }
    output  {
      uses Token;
    }
  }
  /* core/access/service.proto */
  rpc intri-access-Logout {
  }
  /* core/access/service.proto */
  rpc intri-access-PAMLogin {
    input  {
      uses LoginRequest;
    }
    output  {
      uses intri-event:LoginParameter;
    }
  }
  /* core/access/service.proto */
  rpc intri-access-GetUsers {
    output  {
      uses UsersConfig;
    }
  }
  /* core/access/service.proto */
  rpc intri-access-AddUser {
    input  {
      uses UserEntry;
    }
  }
  /* core/access/service.proto */
  rpc intri-access-DeleteUser {
    input  {
      uses intri-common:Name;
    }
  }
  /* core/access/service.proto */
  rpc intri-access-UpdateUser {
    input  {
      uses UserEntry;
    }
  }
  /* core/access/service.proto */
  rpc intri-access-RunEncryptPassword {
    input  {
      uses Password;
    }
    output  {
      uses EncryptedPassword;
    }
  }
  /* core/access/service.proto */
  rpc intri-access-RunUserEnterPassword {
    input  {
      uses UserPassword;
    }
  }
  /* core/access/service.proto */
  rpc intri-access-RunUserEnterSNMPV3AuthPassword {
    input  {
      uses UserPassword;
    }
  }
  /* core/access/service.proto */
  rpc intri-access-RunUserEnterSNMPV3PrivacyPassword {
    input  {
      uses UserPassword;
    }
  }
  /* core/access/service.proto */
  rpc intri-access-GetGroups {
    output  {
      uses GroupsConfig;
    }
  }
  /* core/access/service.proto */
  rpc intri-access-AddGroup {
    input  {
      uses GroupEntry;
    }
  }
  /* core/access/service.proto */
  rpc intri-access-DeleteGroup {
    input  {
      uses intri-common:Name;
    }
  }
  /* core/access/service.proto */
  rpc intri-access-UpdateGroup {
    input  {
      uses GroupEntry;
    }
  }
  /* core/access/service.proto */
  rpc intri-access-GetAuthenticatorServerConfig {
    output  {
      uses AuthenticationServersConfig;
    }
  }
  /* core/access/service.proto */
  rpc intri-access-AddAuthenticatorServerConfig {
    input  {
      uses AuthenticationServerEntry;
    }
  }
  /* core/access/service.proto */
  rpc intri-access-DeleteAuthenticatorServerConfig {
    input  {
      uses intri-common:Name;
    }
  }
  /* core/access/service.proto */
  rpc intri-access-UpdateAuthenticatorServerConfig {
    input  {
      uses AuthenticationServerEntry;
    }
  }
  /* core/access/service.proto */
  rpc intri-access-GetRestrictions {
    output  {
      uses RestrictionsConfig;
    }
  }
  /* core/access/service.proto */
  rpc intri-access-AddRestriction {
    input  {
      uses RestrictionEntry;
    }
  }
  /* core/access/service.proto */
  rpc intri-access-DeleteRestriction {
    input  {
      uses intri-common:Name;
    }
  }
  /* core/access/service.proto */
  rpc intri-access-UpdateRestriction {
    input  {
      uses RestrictionEntry;
    }
  }

}
