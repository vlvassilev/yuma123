module mod1 {
  yang-version 1.1;

  namespace "http://yuma123.org/ns/test/yangcli/identical-identity-names/mod1";
  prefix m1;

  organization
    "yuma123.org";

  description
    'Validation of handling of identities with
     identical names but different module namespace.';

  revision 2018-06-27 {
    description
      "Initial version";
  }

  identity mybase;

  identity myidentity {
    base "mybase";
  }

  container mycontainer {
    leaf myleaf {
      type identityref {
        base "mybase"; 
      }
    }
  }
}
