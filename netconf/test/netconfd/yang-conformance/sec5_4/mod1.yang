module mod1 {
  yang-version 1.1;

  namespace "http://yuma123.org/ns/sec5_4/mod1";
  prefix m1;

  organization
    "yuma123.org";

  description 'sec5_4 Resolving Grouping, Type, and Identity Names';

  revision 2017-07-31 {
    description
      "Initial version";
  }
  container top {
    list entry {
      key name;
      leaf name {
        type string;
      }
    }
  }
  typedef entry-ref {
    type leafref {
      path "/top/entry/name";
    }
  }
}
