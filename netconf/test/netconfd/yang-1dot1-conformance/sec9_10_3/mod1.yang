module mod1 {
  prefix m1;
  namespace "http://yuma123.org/ns/sec9_10_3/mod1";
  reference "https://mailarchive.ietf.org/arch/msg/netmod/D7ASSAQdpGmGXjIdRo_PCnQmVP8";
  identity B;
  identity X {
    base B;
  }
  leaf foo {
    type identityref {
      base B;
    }
  }
}
