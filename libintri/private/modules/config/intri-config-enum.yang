submodule intri-config-enum {
  belongs-to "intri-config" {
    prefix "intri-config-enum";
  }
  revision 2022-06-14 {
    description "Build date.";
  }
  // config/config.proto
  typedef StorageTypeOptions {
    type enumeration {
      enum STORAGE_TYPE_RAM_DISK {
        description "[In RAM Disk] Configuration is saved in RAM dist";
        value 0;
      }
    }
  }
  // config/config.proto
  typedef SaveModeTypeOptions {
    type enumeration {
      enum SAVE_MODE_TYPE_TEMPORARILY {
        description "[Temporarily] Modification on config is temporarily before save.";
        value 0;
      }
    }
  }
  // config/config.proto
  typedef ConfigTypeOptions {
    type enumeration {
      enum CONIFG_TYPE_RUNNING {
        description "[Running] Running Configuration";
        value 0;
      }
      enum CONIFG_TYPE_DEFAULT {
        description "[Default] Default Configuration";
        value 1;
      }
      enum CONIFG_TYPE_SAVE {
        description "[Save] Save Configuration";
        value 2;
      }
    }
  }
  // config/config.proto
  typedef ConfigStateTypeOptions {
    type enumeration {
      enum CONFIG_STATE_TYPE_SAVED {
        description "[Saved] Configuration is saved";
        value 0;
      }
      enum CONFIG_STATE_TYPE_CHANGED {
        description "[Changed] Configuration is changed";
        value 1;
      }
    }
  }
  // config/config.proto
  typedef FactoryDefaultModeTypeOptions {
    type enumeration {
      enum FACTORY_DEFAULT_MODE_TYPE_KEEP_ALL {
        description "[Keep All] Reset default but keep user/network configs";
        value 0;
      }
      enum FACTORY_DEFAULT_MODE_TYPE_KEEP_USER_ACCOUNTS {
        description "[Keep User Accounts] Reset default but keep user accounts";
        value 1;
      }
      enum FACTORY_DEFAULT_MODE_TYPE_KEEP_NETWORK_CONFIGS {
        description "[Keep Network Configs] Reset default but keep network configs";
        value 2;
      }
      enum FACTORY_DEFAULT_MODE_TYPE_RESET_ALL {
        description "[Reset All] Reset to factory default";
        value 3;
      }
    }
  }
}
