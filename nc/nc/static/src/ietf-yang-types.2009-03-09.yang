module ietf-yang-types {

   namespace "urn:ietf:params:xml:ns:yang:yang-types";
   prefix "yang";

   organization
    "IETF NETMOD (NETCONF Data Modeling Language) Working Group";

   contact
    "WG Web:   <http://tools.ietf.org/wg/netmod/>
     WG List:  <mailto:netmod@ietf.org>

     WG Chair: David Partain
               <mailto:david.partain@ericsson.com>

     WG Chair: David Kessens
               <mailto: david.kessens@nsn.com>

     Editor:   Juergen Schoenwaelder
               <mailto:j.schoenwaelder@jacobs-university.de>";

   description
    "This module contains a collection of generally useful derived
     YANG data types.

     Copyright (C) 2009 The IETF Trust and the persons identified as
     the document authors.  This version of this YANG module is part
     of RFC XXXX; see the RFC itself for full legal notices.";
   // RFC Ed.: replace XXXX with actual RFC number and remove this note

   revision 2009-03-09 {
     description
      "Initial revision, published as RFC XXXX.";
   }
   // RFC Ed.: replace XXXX with actual RFC number and remove this note

   /*** collection of counter and gauge types ***/

   typedef counter32 {
     type uint32;
     description
      "The counter32 type represents a non-negative integer
       which monotonically increases until it reaches a
       maximum value of 2^32-1 (4294967295 decimal), when it
       wraps around and starts increasing again from zero.

       Counters have no defined `initial' value, and thus, a
       single value of a counter has (in general) no information
       content.  Discontinuities in the monotonically increasing
       value normally occur at re-initialization of the
       management system, and at other times as specified in the
       description of an object instance using this type.  If
       such other times can occur, for example, the creation of
       an object instance of type counter32 at times other than
       re-initialization, then a corresponding object should be
       defined, with an appropriate type, to indicate the last
       discontinuity.

       The counter32 type should not be used for configuration
       objects. A default statement should not be used for
       attributes with a type value of counter32.

       This type is in the value set and its semantics equivalent
       to the Counter32 type of the SMIv2.";
     reference
      "RFC 2578: Structure of Management Information Version 2 (SMIv2)";
   }

   typedef zero-based-counter32 {
     type yang:counter32;
     default "0";
     description
      "The zero-based-counter32 type represents a counter32
       which has the defined `initial' value zero.

       Objects of this type will be set to zero(0) on creation
       and will thereafter count appropriate events, wrapping
       back to zero(0) when the value 2^32 is reached.

       Provided that an application discovers the new object within
       the minimum time to wrap it can use the initial value as a
       delta since it last polled the table of which this object is
       part.  It is important for a management station to be aware
       of this minimum time and the actual time between polls, and
       to discard data if the actual time is too long or there is
       no defined minimum time.

       This type is in the value set and its semantics equivalent
       to the ZeroBasedCounter32 textual convention of the SMIv2.";
     reference
       "RFC 2021: Remote Network Monitoring Management Information
                  Base Version 2 using SMIv2";
   }

   typedef counter64 {
     type uint64;
     description
      "The counter64 type represents a non-negative integer
       which monotonically increases until it reaches a
       maximum value of 2^64-1 (18446744073709551615), when
       it wraps around and starts increasing again from zero.

       Counters have no defined `initial' value, and thus, a
       single value of a counter has (in general) no information
       content.  Discontinuities in the monotonically increasing
       value normally occur at re-initialization of the
       management system, and at other times as specified in the
       description of an object instance using this type.  If
       such other times can occur, for example, the creation of
       an object instance of type counter64 at times other than
       re-initialization, then a corresponding object should be
       defined, with an appropriate type, to indicate the last
       discontinuity.

       The counter64 type should not be used for configuration
       objects. A default statement should not be used for
       attributes with a type value of counter64.

       This type is in the value set and its semantics equivalent
       to the Counter64 type of the SMIv2.";
     reference
      "RFC 2578: Structure of Management Information Version 2 (SMIv2)";
   }

   typedef zero-based-counter64 {
     type yang:counter64;
     default "0";
     description
      "The zero-based-counter64 type represents a counter64 which
       has the defined `initial' value zero.

       Objects of this type will be set to zero(0) on creation
       and will thereafter count appropriate events, wrapping
       back to zero(0) when the value 2^64 is reached.

       Provided that an application discovers the new object within
       the minimum time to wrap it can use the initial value as a
       delta since it last polled the table of which this object is
       part.  It is important for a management station to be aware
       of this minimum time and the actual time between polls, and
       to discard data if the actual time is too long or there is
       no defined minimum time.

       This type is in the value set and its semantics equivalent
       to the ZeroBasedCounter64 textual convention of the SMIv2.";
     reference
      "RFC 2856: Textual Conventions for Additional High Capacity
                 Data Types";
   }

   typedef gauge32 {
     type uint32;
     description
      "The gauge32 type represents a non-negative integer, which
       may increase or decrease, but shall never exceed a maximum
       value, nor fall below a minimum value.  The maximum value
       can not be greater than 2^32-1 (4294967295 decimal), and
       the minimum value can not be smaller than 0.  The value of
       a gauge32 has its maximum value whenever the information
       being modeled is greater than or equal to its maximum
       value, and has its minimum value whenever the information
       being modeled is smaller than or equal to its minimum value.
       If the information being modeled subsequently decreases
       below (increases above) the maximum (minimum) value, the
       gauge32 also decreases (increases).

       This type is in the value set and its semantics equivalent
       to the Counter32 type of the SMIv2.";
     reference
      "RFC 2578: Structure of Management Information Version 2 (SMIv2)";
   }

   typedef gauge64 {
     type uint64;
     description
      "The gauge64 type represents a non-negative integer, which
       may increase or decrease, but shall never exceed a maximum
       value, nor fall below a minimum value.  The maximum value
       can not be greater than 2^64-1 (18446744073709551615), and
       the minimum value can not be smaller than 0.  The value of
       a gauge64 has its maximum value whenever the information
       being modeled is greater than or equal to its maximum
       value, and has its minimum value whenever the information
       being modeled is smaller than or equal to its minimum value.
       If the information being modeled subsequently decreases
       below (increases above) the maximum (minimum) value, the
       gauge64 also decreases (increases).

       This type is in the value set and its semantics equivalent
       to the CounterBasedGauge64 SMIv2 textual convention defined
       in RFC 2856";

     reference
      "RFC 2856: Textual Conventions for Additional High Capacity
                 Data Types";
   }

   /*** collection of identifier related types ***/

   typedef object-identifier {
     type string {
       pattern '(([0-1](\.[1-3]?[0-9]))|(2\.(0|([1-9]\d*))))'
             + '(\.(0|([1-9]\d*)))*';
     }
     description
      "The object-identifier type represents administratively
       assigned names in a registration-hierarchical-name tree.

       Values of this type are denoted as a sequence of numerical
       non-negative sub-identifier values. Each sub-identifier
       value MUST NOT exceed 2^32-1 (4294967295). Sub-identifiers
       are separated by single dots and without any intermediate
       white space.

       Although the number of sub-identifiers is not limited,
       module designers should realize that there may be
       implementations that stick with the SMIv2 limit of 128
       sub-identifiers.

       This type is a superset of the SMIv2 OBJECT IDENTIFIER type
       since it is not restricted to 128 sub-identifiers.";
     reference
      "ISO/IEC 9834-1: Information technology -- Open Systems
       Interconnection -- Procedures for the operation of OSI
       Registration Authorities: General procedures and top
       arcs of the ASN.1 Object Identifier tree";
   }

   typedef object-identifier-128 {
     type object-identifier {
       pattern '\d*(.\d*){1,127}';
     }
     description
      "This type represents object-identifiers restricted to 128
       sub-identifiers.

       This type is in the value set and its semantics equivalent
       to the OBJECT IDENTIFIER type of the SMIv2.";
     reference
      "RFC 2578: Structure of Management Information Version 2 (SMIv2)";
   }

   /*** collection of date and time related types ***/

   typedef date-and-time {
     type string {
       pattern '\d{4}-\d{2}-\d{2}T\d{2}:\d{2}:\d{2}(\.\d+)?'
             + '(Z|(\+|-)\d{2}:\d{2})';
     }
     description
      'The date-and-time type is a profile of the ISO 8601
       standard for representation of dates and times using the
       Gregorian calendar. The format is most easily described
       using the following ABFN (see RFC 3339):

       date-fullyear   = 4DIGIT
       date-month      = 2DIGIT  ; 01-12
       date-mday       = 2DIGIT  ; 01-28, 01-29, 01-30, 01-31
       time-hour       = 2DIGIT  ; 00-23
       time-minute     = 2DIGIT  ; 00-59
       time-second     = 2DIGIT  ; 00-58, 00-59, 00-60
       time-secfrac    = "." 1*DIGIT
       time-numoffset  = ("+" / "-") time-hour ":" time-minute
       time-offset     = "Z" / time-numoffset

       partial-time    = time-hour ":" time-minute ":" time-second
                         [time-secfrac]
       full-date       = date-fullyear "-" date-month "-" date-mday
       full-time       = partial-time time-offset

       date-time       = full-date "T" full-time

       The date-and-time type is consistent with the semantics defined
       in RFC 3339. The data-and-time type is compatible with the
       dateTime XML schema type with the following two notable
       exceptions:

       (a) The data-and-time type does not allow negative years.

       (b) The data-and-time time-offset -00:00 indicates an unknown
           time zone (see RFC 3339) while -00:00 and +00:00 and Z all
           represent the same time zone in dateTime.

       This type is not equivalent to the DateAndTime textual
       convention of the SMIv2 since RFC 3339 uses a different
       separator between full-date and full-time and provides
       higher resolution of time-secfrac.

       The canonical format for date-and-time values mandates the UTC
       time format with the time-offset is indicated by the letter "Z".
       This is consistent with the canonical format used by the
       dateTime XML schema type.';
     reference
      "RFC 3339: Date and Time on the Internet: Timestamps
       RFC 2579: Textual Conventions for SMIv2
       W3C REC-xmlschema-2-20041028: XML Schema Part 2: Datatypes
                 Second Edition";
   }

   typedef timeticks {
     type uint32;
     description
      "The timeticks type represents a non-negative integer which
       represents the time, modulo 2^32 (4294967296 decimal), in
       hundredths of a second between two epochs. When objects
       are defined which use this type, the description of the
       object identifies both of the reference epochs.

       This type is in the value set and its semantics equivalent
       to the TimeTicks type of the SMIv2.";
     reference
      "RFC 2578: Structure of Management Information Version 2 (SMIv2)";
   }

   typedef timestamp {
     type yang:timeticks;
     description
      "The timestamp type represents the value of an associated
       timeticks object at which a specific occurrence happened.
       The specific occurrence must be defined in the description
       of any object defined using this type.  When the specific
       occurrence occurred prior to the last time the associated
       timeticks attribute was zero, then the timestamp value is
       zero.  Note that this requires all timestamp values to be
       reset to zero when the value of the associated timeticks
       attribute reaches 497+ days and wraps around to zero.

       The associated timeticks object must be specified
       in the description of any object using this type.

       This type is in the value set and its semantics equivalent
       to the TimeStamp textual convention of the SMIv2.";
     reference
      "RFC 2579: Textual Conventions for SMIv2";
   }

   /*** collection of generic address types ***/

   typedef phys-address {
     type string {
       pattern '([0-9a0-fA-F]{2}(:[0-9a0-fA-F]{2})*)?';
     }
     description
      "Represents media- or physical-level addresses represented
       as a sequence octets, each octet represented by two hexadecimal
       numbers. Octets are separated by colons.

       This type is in the value set and its semantics equivalent
       to the PhysAddress textual convention of the SMIv2.";
     reference
      "RFC 2579: Textual Conventions for SMIv2";
   }

   /*** collection of XML specific types ***/

   typedef xpath {               // [TODO] call this xpath1-0?
     type string;
     description
      "This type represents an XPATH 1.0 expression.";
      // [TODO] Normalization needed due to abbreviated syntax and the
      // unabbreviated syntax? Whitespace stuff to take care of?
     reference
      "W3C REC-xpath-19991116: XML Path Language (XPath) Version 1.0";
   }

 }
