module intri-timeofday {

  namespace "intri:intri-timeofday";
  prefix "intri-timeofday";
  organization "
    Intrising Inc.";
  contact "
    intrising@intrising.com.tw";
  revision 2022-06-24 {
    description "Build date.";
  }

  grouping TimeOfDay {
    leaf Hours {
      mandatory "true";
      type int32;
    }
    leaf Minutes {
      mandatory "true";
      type int32;
    }
    leaf Seconds {
      mandatory "true";
      type int32;
    }
    leaf Nanos {
      mandatory "true";
      type int32;
    }
  }
}
