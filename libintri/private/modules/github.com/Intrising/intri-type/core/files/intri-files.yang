// Code generated by protoc-gen-yang. DO NOT EDIT.


/* ****************************************************************************************************
 * Import Path : "github.com/Intrising/intri-type/core/files"                                         *
 * Dir Path    : github.com/Intrising/intri-type/core/files                                           *
 * Go Package  : files                                                                                *
 * Files       : 2                                                                                    *
 **************************************************************************************************** */
module intri-files {

  namespace "intri:intri-files";

  prefix "intri-files";

  organization "Intrising Inc.";

  contact "intrising@intrising.com.tw";

  revision 2022-06-23 {
    description "Build date.";
  }

  import intri-empty {
    prefix intri-empty;
  }
  import intri-common {
    prefix intri-common;
  }


  /* **************************************************************************************************
   * Enums       : 1                                                                                  *
   ************************************************************************************************** */
  /* core/files/files.proto */
  typedef CertificateTypeOptions {
    type enumeration {
      enum CERTIFICATE_TYPE_WEB {
        description "[Web]";
        value 0;
      }
      enum CERTIFICATE_TYPE_SNMP {
        description "[SNMP]";
        value 1;
      }
    }
  }


  /* **************************************************************************************************
   * Msgs        : 9                                                                                  *
   ************************************************************************************************** */
  /* core/files/files.proto */
  grouping Config {
    leaf FTPEnabled {
      type boolean;
    }
    container Certificate {
      uses ActivateCertificate;
    }
  }
  /* core/files/files.proto */
  grouping ActivateCertificate {
    container Web {
      uses CertificateID;
    }
    container SnmpAgent {
      uses CertificateID;
    }
    container SnmpManager {
      uses CertificateUserIDList;
    }
  }
  /* core/files/files.proto */
  grouping CertificateID {
    leaf ID {
      type string;
    }
  }
  /* core/files/files.proto */
  grouping CertificateIDList {
    container List {
      leaf-list List_Entry {
        type string;
      }
    }
  }
  /* core/files/files.proto */
  grouping CertificateData {
    leaf ID {
      type string;
    }
    leaf CrtPath {
      type string;
    }
    leaf KeyPath {
      type string;
    }
    leaf FTPSEnabled {
      type boolean;
    }
    leaf AuthCrtPath {
      type string;
    }
  }
  /* core/files/files.proto */
  grouping CertificateUserID {
    leaf ID {
      type string;
    }
    leaf Username {
      type string;
    }
  }
  /* core/files/files.proto */
  grouping CertificateUserIDList {
    container List {
      list List_Entry {
        uses CertificateUserID;
      }
    }
  }
  /* core/files/files.proto */
  grouping CertificateType {
    leaf Type {
      type CertificateTypeOptions;
    }
  }
  /* core/files/files.proto */
  grouping CertificateInfo {
    leaf CrtPath {
      type string;
    }
    leaf KeyPath {
      type string;
    }
    leaf Passphrase {
      type string;
    }
    leaf AuthCrtPath {
      type string;
    }
  }


  /* **************************************************************************************************
   * Services    : 1                                                                                  *
   ************************************************************************************************** */

  /* **************************************************************************************************
   * Service     : Files                                                                              *
   * Methods     : 14                                                                                 *
   ************************************************************************************************** */
  /* core/files/service.proto */
  rpc intri-files-GetConfig {
    output  {
      uses Config;
    }
  }
  /* core/files/service.proto */
  rpc intri-files-GetFTPServerEnabled {
    output  {
      uses intri-common:Enabled;
    }
  }
  /* core/files/service.proto */
  rpc intri-files-SetFTPServerEnabled {
    input  {
      uses intri-common:Enabled;
    }
  }
  /* core/files/service.proto */
  rpc intri-files-GetActivateCertificate {
    output  {
      uses ActivateCertificate;
    }
  }
  /* core/files/service.proto */
  rpc intri-files-SetActivateCertificateForWeb {
    input  {
      uses CertificateID;
    }
  }
  /* core/files/service.proto */
  rpc intri-files-SetActivateCertificateForSNMP {
    input  {
      uses CertificateID;
    }
  }
  /* core/files/service.proto */
  rpc intri-files-AddActivateCertificateForSNMPManager {
    input  {
      uses CertificateUserID;
    }
  }
  /* core/files/service.proto */
  rpc intri-files-DeleteActivateCertificateForSNMPManager {
    input  {
      uses CertificateUserID;
    }
  }
  /* core/files/service.proto */
  rpc intri-files-UpdateActivateCertificateForSNMPManager {
    input  {
      uses CertificateUserID;
    }
  }
  /* core/files/service.proto */
  rpc intri-files-RunImportCertificate {
    input  {
      uses CertificateData;
    }
  }
  /* core/files/service.proto */
  rpc intri-files-RunExportCertificate {
    input  {
      uses CertificateData;
    }
  }
  /* core/files/service.proto */
  rpc intri-files-RunRemoveCertificate {
    input  {
      uses CertificateID;
    }
  }
  /* core/files/service.proto */
  rpc intri-files-GetCertificateList {
    output  {
      uses CertificateIDList;
    }
  }
  /* core/files/service.proto */
  rpc intri-files-GetActivateCertificateInfo {
    input  {
      uses CertificateType;
    }
    output  {
      uses CertificateInfo;
    }
  }

}
