module testmalloc {

    namespace "urn:ietf:params:xml:ns:yang:testmalloc";
    prefix "tm";

    revision 2008-10-15 {
        description "Initial revision.";
    }

    leaf leafref1 {
       type leafref {
          path "../foo";
       }
    }

    leaf foo { type int32; }

}
