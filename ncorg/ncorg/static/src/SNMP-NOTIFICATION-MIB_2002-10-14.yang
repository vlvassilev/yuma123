/*
 * This module has been generated by smidump 0.4.6:
 *
 *      smidump -f yang --yang-smi-extensions SNMP-NOTIFICATION-MIB
 *
 * Do not edit. Edit the source file instead!
 */

module SNMP-NOTIFICATION-MIB {

   /*** NAMESPACE / PREFIX DEFINITION ***/

   namespace "urn:ietf:params:xml:ns:yang:smiv2:SNMP-NOTIFICATION-MIB";
   prefix "snmp-notification";

   /*** LINKAGE (IMPORTS / INCLUDES) ***/

   import SNMP-FRAMEWORK-MIB { prefix "snmp-framework"; }
   import SNMP-TARGET-MIB    { prefix "snmp-target"; }
   import SNMPv2-TC          { prefix "smiv2"; }
   import yang-smi           { prefix "smi"; }
   import yang-types         { prefix "yang"; }

   /*** META INFORMATION ***/

   organization     
     "IETF SNMPv3 Working Group";

   contact          
     "WG-email:   snmpv3@lists.tislabs.com
      Subscribe:  majordomo@lists.tislabs.com
                  In message body:  subscribe snmpv3
      
      Co-Chair:   Russ Mundy
                  Network Associates Laboratories
      Postal:     15204 Omega Drive, Suite 300
                  Rockville, MD 20850-4601
                  USA
      EMail:      mundy@tislabs.com
      Phone:      +1 301-947-7107
      
      Co-Chair:   David Harrington
                  Enterasys Networks
      Postal:     35 Industrial Way
                  P. O. Box 5004
                  Rochester, New Hampshire 03866-5005
                  USA
      EMail:      dbh@enterasys.com
      Phone:      +1 603-337-2614
      
      Co-editor:  David B. Levi
                  Nortel Networks
      Postal:     3505 Kesterwood Drive
                  Knoxville, Tennessee 37918
      EMail:      dlevi@nortelnetworks.com
      Phone:      +1 865 686 0432
      
      Co-editor:  Paul Meyer
                  Secure Computing Corporation
      Postal:     2675 Long Lake Road
                  Roseville, Minnesota 55113
      EMail:      paul_meyer@securecomputing.com
      Phone:      +1 651 628 1592
      
      Co-editor:  Bob Stewart
                  Retired";

   description      
     "This MIB module defines MIB objects which provide
      mechanisms to remotely configure the parameters
      used by an SNMP entity for the generation of
      notifications.
      
      Copyright (C) The Internet Society (2002). This
      version of this MIB module is part of RFC 3413;
      see the RFC itself for full legal notices.";

   revision "2002-10-14" {
      description   
        "Clarifications, published as
         RFC 3413.";
   }
   revision "1998-08-04" {
      description   
        "Clarifications, published as
         RFC 2573.";
   }
   revision "1997-07-14" {
      description   
        "The initial revision, published as RFC2273.";
   }

   container snmpNotifyObjects {


      /* XXX table comments here XXX */

      list snmpNotifyEntry {

         key "snmpNotifyName";
         description 
           "An entry in this table selects a set of management targets
            which should receive notifications, as well as the type of
            
            notification which should be sent to each selected
            management target.
            
            Entries in the snmpNotifyTable are created and
            deleted using the snmpNotifyRowStatus object.";
         smi:oid "1.3.6.1.6.3.13.1.1.1";


         leaf snmpNotifyName {
            type snmp-framework:SnmpAdminString {
               length "1..32";
            }
            config false;
            description   
              "The locally arbitrary, but unique identifier associated
               with this snmpNotifyEntry.";
            smi:oid "1.3.6.1.6.3.13.1.1.1.1";
         }

         leaf snmpNotifyTag {
            type snmp-target:SnmpTagValue;
            config true;
            description   
              "This object contains a single tag value which is used
               to select entries in the snmpTargetAddrTable.  Any entry
               in the snmpTargetAddrTable which contains a tag value
               which is equal to the value of an instance of this
               object is selected.  If this object contains a value
               of zero length, no entries are selected.";
            smi:default "";
            smi:oid "1.3.6.1.6.3.13.1.1.1.2";
         }

         leaf snmpNotifyType {
            type enumeration {
               enum trap   { value 1; }
               enum inform { value 2; }
            }
            config true;
            description   
              "This object determines the type of notification to
               
               be generated for entries in the snmpTargetAddrTable
               selected by the corresponding instance of
               snmpNotifyTag.  This value is only used when
               generating notifications, and is ignored when
               using the snmpTargetAddrTable for other purposes.
               
               If the value of this object is trap(1), then any
               messages generated for selected rows will contain
               Unconfirmed-Class PDUs.
               
               If the value of this object is inform(2), then any
               messages generated for selected rows will contain
               Confirmed-Class PDUs.
               
               Note that if an SNMP entity only supports
               generation of Unconfirmed-Class PDUs (and not
               Confirmed-Class PDUs), then this object may be
               read-only.";
            smi:default "trap";
            smi:oid "1.3.6.1.6.3.13.1.1.1.3";
         }

         leaf snmpNotifyStorageType {
            type smiv2:StorageType;
            config true;
            description   
              "The storage type for this conceptual row.
               Conceptual rows having the value 'permanent' need not
               allow write-access to any columnar objects in the row.";
            smi:default "nonVolatile";
            smi:oid "1.3.6.1.6.3.13.1.1.1.4";
         }

         leaf snmpNotifyRowStatus {
            type smiv2:RowStatus;
            config true;
            description   
              "The status of this conceptual row.
               
               To create a row in this table, a manager must
               set this object to either createAndGo(4) or
               createAndWait(5).";
            smi:oid "1.3.6.1.6.3.13.1.1.1.5";
         }
      }


      /* XXX table comments here XXX */

      list snmpNotifyFilterProfileEntry {

         key "snmpTargetParamsName";
         description 
           "An entry in this table indicates the name of the filter
            profile to be used when generating notifications using
            the corresponding entry in the snmpTargetParamsTable.
            
            Entries in the snmpNotifyFilterProfileTable are created
            and deleted using the snmpNotifyFilterProfileRowStatus
            object.";
         smi:oid "1.3.6.1.6.3.13.1.2.1";

         leaf snmpTargetParamsName {
            type keyref {
               path "/snmp-target:snmpTargetObjects/snmp-target:snmpTargetParamsEntry/snmp-target:snmpTargetParamsName";
            }
            config true;
            description   
              "Automagically generated keyref leaf.";
         }

         leaf snmpNotifyFilterProfileName {
            type snmp-framework:SnmpAdminString {
               length "1..32";
            }
            config true;
            description   
              "The name of the filter profile to be used when generating
               notifications using the corresponding entry in the
               snmpTargetAddrTable.";
            smi:oid "1.3.6.1.6.3.13.1.2.1.1";
         }

         leaf snmpNotifyFilterProfileStorType {
            type smiv2:StorageType;
            config true;
            description   
              "The storage type for this conceptual row.
               Conceptual rows having the value 'permanent' need not
               allow write-access to any columnar objects in the row.";
            smi:default "nonVolatile";
            smi:oid "1.3.6.1.6.3.13.1.2.1.2";
         }

         leaf snmpNotifyFilterProfileRowStatus {
            type smiv2:RowStatus;
            config true;
            description   
              "The status of this conceptual row.
               
               To create a row in this table, a manager must
               set this object to either createAndGo(4) or
               createAndWait(5).
               
               Until instances of all corresponding columns are
               appropriately configured, the value of the
               corresponding instance of the
               snmpNotifyFilterProfileRowStatus column is 'notReady'.
               
               In particular, a newly created row cannot be made
               active until the corresponding instance of
               snmpNotifyFilterProfileName has been set.";
            smi:oid "1.3.6.1.6.3.13.1.2.1.3";
         }
      }


      /* XXX table comments here XXX */

      list snmpNotifyFilterEntry {

         key "snmpNotifyFilterProfileName 
              snmpNotifyFilterSubtree";
         description 
           "An element of a filter profile.
            
            Entries in the snmpNotifyFilterTable are created and
            deleted using the snmpNotifyFilterRowStatus object.";
         smi:oid "1.3.6.1.6.3.13.1.3.1";

         leaf snmpNotifyFilterProfileName {
            type keyref {
               path "/snmp-notification:snmpNotifyObjects/snmp-notification:snmpNotifyFilterProfileEntry/snmp-notification:snmpNotifyFilterProfileName";
            }
            config true;
            description   
              "Automagically generated keyref leaf.";
         }

         leaf snmpNotifyFilterSubtree {
            type yang:object-identifier;
            config false;
            description   
              "The MIB subtree which, when combined with the corresponding
               instance of snmpNotifyFilterMask, defines a family of
               subtrees which are included in or excluded from the
               filter profile.";
            smi:oid "1.3.6.1.6.3.13.1.3.1.1";
         }

         leaf snmpNotifyFilterMask {
            type binary {
               length "0..16";
            }
            config true;
            description   
              "The bit mask which, in combination with the corresponding
               instance of snmpNotifyFilterSubtree, defines a family of
               subtrees which are included in or excluded from the
               filter profile.
               
               Each bit of this bit mask corresponds to a
               sub-identifier of snmpNotifyFilterSubtree, with the
               most significant bit of the i-th octet of this octet
               string value (extended if necessary, see below)
               corresponding to the (8*i - 7)-th sub-identifier, and
               the least significant bit of the i-th octet of this
               octet string corresponding to the (8*i)-th
               sub-identifier, where i is in the range 1 through 16.
               
               Each bit of this bit mask specifies whether or not
               the corresponding sub-identifiers must match when
               determining if an OBJECT IDENTIFIER matches this
               family of filter subtrees; a '1' indicates that an
               exact match must occur; a '0' indicates 'wild card',
               i.e., any sub-identifier value matches.
               
               Thus, the OBJECT IDENTIFIER X of an object instance
               is contained in a family of filter subtrees if, for
               each sub-identifier of the value of
               snmpNotifyFilterSubtree, either:
               
                 the i-th bit of snmpNotifyFilterMask is 0, or
               
                 the i-th sub-identifier of X is equal to the i-th
                 sub-identifier of the value of
                 snmpNotifyFilterSubtree.
               
               If the value of this bit mask is M bits long and
               there are more than M sub-identifiers in the
               corresponding instance of snmpNotifyFilterSubtree,
               then the bit mask is extended with 1's to be the
               required length.
               
               Note that when the value of this object is the
               zero-length string, this extension rule results in
               a mask of all-1's being used (i.e., no 'wild card'),
               and the family of filter subtrees is the one
               subtree uniquely identified by the corresponding
               instance of snmpNotifyFilterSubtree.";
            smi:default "";
            smi:oid "1.3.6.1.6.3.13.1.3.1.2";
         }

         leaf snmpNotifyFilterType {
            type enumeration {
               enum included { value 1; }
               enum excluded { value 2; }
            }
            config true;
            description   
              "This object indicates whether the family of filter subtrees
               defined by this entry are included in or excluded from a
               filter.  A more detailed discussion of the use of this
               object can be found in section 6. of [SNMP-APPL].";
            smi:default "included";
            smi:oid "1.3.6.1.6.3.13.1.3.1.3";
         }

         leaf snmpNotifyFilterStorageType {
            type smiv2:StorageType;
            config true;
            description   
              "The storage type for this conceptual row.
               Conceptual rows having the value 'permanent' need not
               
               allow write-access to any columnar objects in the row.";
            smi:default "nonVolatile";
            smi:oid "1.3.6.1.6.3.13.1.3.1.4";
         }

         leaf snmpNotifyFilterRowStatus {
            type smiv2:RowStatus;
            config true;
            description   
              "The status of this conceptual row.
               
               To create a row in this table, a manager must
               set this object to either createAndGo(4) or
               createAndWait(5).";
            smi:oid "1.3.6.1.6.3.13.1.3.1.5";
         }
      }
      smi:oid "1.3.6.1.6.3.13.1";
   }

} /* end of module SNMP-NOTIFICATION-MIB */
