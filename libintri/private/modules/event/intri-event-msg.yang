submodule intri-event-msg {
  belongs-to "intri-event" {
    prefix "intri-event-msg";
  }
  include intri-event-enum;
  import eventpb {
    prefix "eventpb";
  }
  import devicepb {
    prefix "devicepb";
  }
  import protobufpb {
    prefix "protobufpb";
  }
  revision 2022-06-14 {
    description "Build date.";
  }
  // event/acl.proto
  grouping ACLParameter {
    leaf ACLParameter_Name {
      type string;
    }
    leaf ACLParameter_Index {
      type int32;
    }
    leaf ACLParameter_Type {
      type eventpb:ACLActionTypeOptions;
    }
  }
  // event/aggregation.proto
  grouping LgportUsed {
    leaf LgportUsed_Action {
      type eventpb:AggrTypeOptions;
    }
    container LgportUsed_OriginalMembers {
      uses devicepb:InterfaceIdentify;
    }
    container LgportUsed_NewMembers {
      uses devicepb:InterfaceIdentify;
    }
    container LgportUsed_AddedMembers {
      uses devicepb:InterfaceIdentify;
    }
    container LgportUsed_DeletedMembers {
      uses devicepb:InterfaceIdentify;
    }
  }
  // event/aggregation.proto
  grouping ProtocolUsed {
    container ProtocolUsed_UpdateMembers {
      uses devicepb:InterfaceIdentify;
    }
  }
  // event/aggregation.proto
  grouping AggrParameter {
    leaf AggrParameter_Type {
      type eventpb:AggrSourceTypeOptions;
    }
    leaf AggrParameter_TrunkID {
      type int32;
    }
    container AggrParameter_Lgport {
      uses eventpb:LgportUsed;
    }
    container AggrParameter_Protocol {
      uses eventpb:ProtocolUsed;
    }
  }
  // event/au.proto
  grouping AUParameter {
    leaf AUParameter_Type {
      type eventpb:AUParameterTypeOptions;
    }
    container AUParameter_Entry {
      uses eventpb:FDBEntry;
    }
  }
  // event/au.proto
  grouping FDBEntry {
    container FDBEntry_IdentifyNo {
      uses devicepb:InterfaceIdentify;
    }
    leaf FDBEntry_IsStatic {
      type boolean;
    }
    leaf FDBEntry_IsForward {
      type boolean;
    }
    leaf FDBEntry_Address {
      type string;
    }
    leaf FDBEntry_VlanID {
      type int32;
    }
    leaf FDBEntry_IsAgeout {
      type boolean;
    }
    leaf FDBEntry_Action {
      type eventpb:FDBEntryActionTypeOptions;
    }
  }
  // event/button.proto
  grouping ButtonParameter {
    leaf ButtonParameter_Type {
      type eventpb:ButtonTypeOptions;
    }
    leaf ButtonParameter_Action {
      type eventpb:ButtonActionTypeOptions;
    }
    leaf ButtonParameter_Trigger {
      type eventpb:ButtonTriggerActionTypeOptions;
    }
  }
  // event/crypto.proto
  grouping CryptoRequest {
    leaf CryptoRequest_Value {
      type string;
    }
    leaf CryptoRequest_Type {
      type eventpb:CryptoTypeOptions;
    }
  }
  // event/crypto.proto
  grouping CryptoResponse {
    leaf CryptoResponse_Value {
      type string;
    }
  }
  // event/crypto.proto
  grouping CryptoBase64Request {
    leaf CryptoBase64Request_Value {
      type uint8;
    }
  }
  // event/crypto.proto
  grouping CryptoBase64Response {
    leaf CryptoBase64Response_Value {
      type uint8;
    }
  }
  // event/dhcp.proto
  grouping DHCPParameter {
    leaf DHCPParameter_TFTPServer {
      type string;
    }
    leaf DHCPParameter_BootFile {
      type string;
    }
    leaf DHCPParameter_Type {
      type eventpb:DHCPClientTypeOptions;
    }
  }
  // event/fdb.proto
  grouping FDBParameter {
    leaf FDBParameter_Type {
      type eventpb:FDBParameterTypeOptions;
    }
    container FDBParameter_Port {
      uses devicepb:InterfaceIdentify;
    }
  }
  // event/initialize.proto
  grouping ServiceInitialized {
    leaf ServiceInitialized_ServiceType {
      type string;
    }
    leaf ServiceInitialized_Action {
      type eventpb:ServiceActionTypeOptions;
    }
  }
  // event/layer.proto
  grouping EthernetLayer {
    leaf EthernetLayer_DstMACAddr {
      type uint8;
    }
    leaf EthernetLayer_DstMACAddrEnabled {
      type boolean;
    }
    leaf EthernetLayer_SrcMACAddr {
      type uint8;
    }
    leaf EthernetLayer_SrcMACAddrEnabled {
      type boolean;
    }
    leaf EthernetLayer_EtherType {
      type eventpb:EthernetTypeOptions;
    }
    leaf EthernetLayer_EtherTypeEnabled {
      type boolean;
    }
  }
  // event/layer.proto
  grouping LLCLayer {
    leaf LLCLayer_DSAP {
      type uint32;
    }
    leaf LLCLayer_DSAPEnabled {
      type boolean;
    }
    leaf LLCLayer_IG {
      type boolean;
    }
    leaf LLCLayer_IGEnabled {
      type boolean;
    }
    leaf LLCLayer_SSAP {
      type uint32;
    }
    leaf LLCLayer_SSAPEnabled {
      type boolean;
    }
    leaf LLCLayer_CR {
      type boolean;
    }
    leaf LLCLayer_CREnabled {
      type boolean;
    }
    leaf LLCLayer_Control {
      type uint32;
    }
    leaf LLCLayer_ControlEnabled {
      type boolean;
    }
  }
  // event/layer.proto
  grouping IPLayer {
    leaf IPLayer_IPProtocol {
      type eventpb:IPProtocolTypeOptions;
    }
    leaf IPLayer_IPProtocolEnabled {
      type boolean;
    }
    leaf IPLayer_SrcIPAddr {
      type uint8;
    }
    leaf IPLayer_SrcIPAddrEnabled {
      type boolean;
    }
    leaf IPLayer_DstIPAddr {
      type uint8;
    }
    leaf IPLayer_DstIPAddrEnabled {
      type boolean;
    }
  }
  // event/layer.proto
  grouping Layer4Port {
    leaf Layer4Port_L4SrcPort {
      type uint32;
    }
    leaf Layer4Port_L4SrcPortEnabled {
      type boolean;
    }
    leaf Layer4Port_L4DstPort {
      type uint32;
    }
    leaf Layer4Port_L4DstPortEnabled {
      type boolean;
    }
  }
  // event/linkchange.proto
  grouping LinkParameter {
    container LinkParameter_IdentifyNo {
      uses devicepb:InterfaceIdentify;
    }
    leaf LinkParameter_Type {
      type eventpb:LinkTypeOptions;
    }
  }
  // event/login.proto
  grouping LoginParameter {
    leaf LoginParameter_Type {
      type eventpb:LoginTypeOptions;
    }
    leaf LoginParameter_Result {
      type eventpb:LoginResultTypeOptions;
    }
    leaf LoginParameter_InterfaceName {
      type eventpb:LoginInterfaceNameTypeOptions;
    }
    leaf LoginParameter_Name {
      type string;
    }
    leaf LoginParameter_Privilege {
      type int32;
    }
    leaf LoginParameter_Token {
      type string;
    }
    leaf LoginParameter_AccessToken {
      type string;
    }
    leaf LoginParameter_ErrCode {
      type string;
    }
    leaf LoginParameter_IPAddress {
      type string;
    }
  }
  // event/maintenance.proto
  grouping MaintenanceParameter {
    leaf MaintenanceParameter_Action {
      type eventpb:MaintenanceActionTypeOptions;
    }
  }
  // event/multicast.proto
  grouping MulticastParameter {
    leaf MulticastParameter_Type {
      type eventpb:MulticastActionTypeOptions;
    }
    leaf MulticastParameter_VlanID {
      type int32;
    }
    leaf MulticastParameter_Addr {
      type string;
    }
  }
  // event/packet.proto
  grouping PacketProbe {
    container PacketProbe_List {
      uses eventpb:PacketProbeEntry;
    }
    leaf PacketProbe_IsPhysicalPort {
      type boolean;
    }
  }
  // event/packet.proto
  grouping PacketProbeEntry {
    container PacketProbeEntry_Ethernet {
      uses eventpb:EthernetLayer;
    }
    leaf PacketProbeEntry_EthernetEnabled {
      type boolean;
    }
    container PacketProbeEntry_LLC {
      uses eventpb:LLCLayer;
    }
    leaf PacketProbeEntry_LLCEnabled {
      type boolean;
    }
    container PacketProbeEntry_IP {
      uses eventpb:IPLayer;
    }
    leaf PacketProbeEntry_IPEnabled {
      type boolean;
    }
    container PacketProbeEntry_L4 {
      uses eventpb:Layer4Port;
    }
    leaf PacketProbeEntry_L4Enabled {
      type boolean;
    }
  }
  // event/packet.proto
  grouping PacketInfo {
    container PacketInfo_Identify {
      uses devicepb:InterfaceIdentify;
    }
    leaf PacketInfo_Forward {
      type boolean;
    }
    leaf PacketInfo_VlanTagged {
      type boolean;
    }
    leaf PacketInfo_EgressFilter {
      type boolean;
    }
    container PacketInfo_ExcludeIdentify {
      uses devicepb:InterfaceIdentify;
    }
  }
  // event/packet.proto
  grouping PacketContent {
    container PacketContent_Info {
      uses eventpb:PacketInfo;
    }
    leaf PacketContent_Buf {
      type uint8;
    }
  }
  // event/poe.proto
  grouping PoEParameter {
    leaf PoEParameter_Type {
      type eventpb:PoEParameterTypeOptions;
    }
    leaf PoEParameter_PortNo {
      type int32;
    }
  }
  // event/port.proto
  grouping PortParameter {
    leaf PortParameter_DeviceID {
      type int32;
    }
    leaf PortParameter_PortNo {
      type int32;
    }
    leaf PortParameter_Enabled {
      type boolean;
    }
  }
  // event/portauth.proto
  grouping PortAuthParameter {
    container PortAuthParameter_IdentifyNo {
      uses devicepb:InterfaceIdentify;
    }
    leaf PortAuthParameter_VlanID {
      type int32;
    }
    leaf PortAuthParameter_MACAddress {
      type string;
    }
  }
  // event/sfp.proto
  grouping SFPInfo {
    leaf SFPInfo_DeviceID {
      type int32;
    }
    leaf SFPInfo_PortNo {
      type int32;
    }
    leaf SFPInfo_Location {
      type string;
    }
    leaf SFPInfo_Status {
      type eventpb:SFPStatusTypeOptions;
    }
    leaf SFPInfo_Type {
      type eventpb:SFPTypeOptions;
    }
    leaf SFPInfo_Connector {
      type eventpb:SFPConnectorTypeOptions;
    }
    leaf SFPInfo_Wavelength {
      type string;
    }
    leaf SFPInfo_TxTechnology {
      type string;
    }
    leaf SFPInfo_RxTechnology {
      type string;
    }
    leaf SFPInfo_NominalBitrate {
      type string;
    }
    leaf SFPInfo_Manufacturer {
      type string;
    }
    leaf SFPInfo_PartNumber {
      type string;
    }
    leaf SFPInfo_Revision {
      type string;
    }
    leaf SFPInfo_SerialNumber {
      type string;
    }
    leaf SFPInfo_MfgDateCode {
      type string;
    }
    leaf SFPInfo_TxPower {
      type string;
    }
    leaf SFPInfo_RxPower {
      type string;
    }
    leaf SFPInfo_Temperature {
      type string;
    }
    leaf SFPInfo_MaxLength9Um {
      type string;
    }
    leaf SFPInfo_MaxLength50Um {
      type string;
    }
    leaf SFPInfo_MaxLength62Um {
      type string;
    }
    leaf SFPInfo_MaxLengthCopper {
      type string;
    }
    leaf SFPInfo_TuningRange {
      type string;
    }
    leaf SFPInfo_PowerConsumption {
      type string;
    }
    leaf SFPInfo_AdditionalInformation {
      type string;
    }
    leaf SFPInfo_Speed {
      type eventpb:PortSpeedDuplexTypeOptions;
    }
  }
  // event/sfp.proto
  grouping SFPParameter {
    leaf SFPParameter_Type {
      type eventpb:SFPActionTypeOptions;
    }
    leaf SFPParameter_DeviceID {
      type int32;
    }
    leaf SFPParameter_PortNo {
      type int32;
    }
    container SFPParameter_Info {
      uses eventpb:SFPInfo;
    }
  }
  // event/stormcontrol.proto
  grouping StormcontrolParameter {
    leaf StormcontrolParameter_ActionOption {
      type eventpb:StormcontrolActionTypeOptions;
    }
    container StormcontrolParameter_IdentifyNo {
      uses devicepb:InterfaceIdentify;
    }
  }
  // event/system.proto
  grouping BootParameter {
    leaf BootParameter_Type {
      type eventpb:BootActionTypeOptions;
    }
    leaf BootParameter_Version {
      type string;
    }
  }
  // event/system.proto
  grouping NetworkParameter {
    container NetworkParameter_Inf {
      uses devicepb:InterfaceIdentify;
    }
    leaf NetworkParameter_IPAddress {
      type string;
    }
    leaf NetworkParameter_SubnetMask {
      type string;
    }
    leaf NetworkParameter_Type {
      type eventpb:NetworkIPv6TypeOptions;
    }
  }
  // event/timerange.proto
  grouping TimeRangeParameter {
    leaf TimeRangeParameter_Name {
      type string;
    }
    leaf TimeRangeParameter_IsActive {
      type boolean;
    }
  }
  // event/udld.proto
  grouping UdldParameter {
    leaf UdldParameter_ActionOption {
      type eventpb:UdldActionTypeOptions;
    }
    container UdldParameter_PortShutdown {
      uses eventpb:UdldActionPortShutdown;
    }
  }
  // event/udld.proto
  grouping UdldActionPortShutdown {
    container UdldActionPortShutdown_IdentifyNo {
      uses devicepb:InterfaceIdentify;
    }
  }
  // event/vlan.proto
  grouping VLANParameter {
    leaf VLANParameter_Type {
      type eventpb:VLANParameterTypeOptions;
    }
    leaf VLANParameter_VlanID {
      type int32;
    }
    leaf VLANParameter_DeviceID {
      type int32;
    }
    container VLANParameter_IdentifyNo {
      uses devicepb:InterfaceIdentify;
    }
  }
  // event/event.proto
  grouping ManagmentVLANPriority {
    leaf ManagmentVLANPriority_Priority {
      type int32;
    }
  }
  // event/event.proto
  grouping InternalTypeUnion {
    leaf InternalTypeUnion_List {
      type eventpb:InternalTypeOptions;
    }
  }
  // event/event.proto
  grouping Internal {
    leaf Internal_Type {
      type eventpb:InternalTypeOptions;
    }
    leaf Internal_Message {
      type string;
    }
    container Internal_Ts {
      uses protobufpb:Timestamp;
    }
    leaf Internal_LoggingType {
      type eventpb:LoggingTypeOptions;
    }
    container Internal_Init {
      uses eventpb:ServiceInitialized;
    }
    container Internal_Vlan {
      uses eventpb:VLANParameter;
    }
    container Internal_DHCP {
      uses eventpb:DHCPParameter;
    }
    container Internal_Login {
      uses eventpb:LoginParameter;
    }
    container Internal_Link {
      uses eventpb:LinkParameter;
    }
    container Internal_Aggr {
      uses eventpb:AggrParameter;
    }
    leaf Internal_NTP {
      type eventpb:NTPActionTypeOptions;
    }
    container Internal_Boot {
      uses eventpb:BootParameter;
    }
    container Internal_Network {
      uses eventpb:NetworkParameter;
    }
    container Internal_Maintenance {
      uses eventpb:MaintenanceParameter;
    }
    container Internal_SFP {
      uses eventpb:SFPParameter;
    }
    container Internal_Port {
      uses eventpb:PortParameter;
    }
    container Internal_PortAuth {
      uses eventpb:PortAuthParameter;
    }
    container Internal_FDB {
      uses eventpb:FDBParameter;
    }
    container Internal_AU {
      uses eventpb:AUParameter;
    }
    container Internal_PoE {
      uses eventpb:PoEParameter;
    }
    container Internal_ACL {
      uses eventpb:ACLParameter;
    }
    container Internal_TimeRange {
      uses eventpb:TimeRangeParameter;
    }
    container Internal_Button {
      uses eventpb:ButtonParameter;
    }
    container Internal_Stormcontrol {
      uses eventpb:StormcontrolParameter;
    }
    container Internal_Multicast {
      uses eventpb:MulticastParameter;
    }
    container Internal_Udld {
      uses eventpb:UdldParameter;
    }
  }
  // event/target.proto
  grouping TargetLogTypeUnion {
    leaf TargetLogTypeUnion_List {
      type eventpb:TargetLogTypeOptions;
    }
  }
  // event/target.proto
  grouping TargetSNMP {
    leaf TargetSNMP_HostAddress {
      type string;
    }
    leaf TargetSNMP_SnmpCommunity {
      type string;
    }
    leaf TargetSNMP_SnmpV3Username {
      type string;
    }
  }
  // event/target.proto
  grouping TargetCLI {
  }
  // event/target.proto
  grouping TargetSysLog {
    leaf TargetSysLog_HostAddress {
      type string;
    }
  }
  // event/target.proto
  grouping TargetLogOptionalParameter {
    leaf TargetLogOptionalParameter_Option {
      type eventpb:TargetLogTypeOptions;
    }
    container TargetLogOptionalParameter_Snmp {
      uses eventpb:TargetSNMP;
    }
    container TargetLogOptionalParameter_Cli {
      uses eventpb:TargetCLI;
    }
    container TargetLogOptionalParameter_SysLog {
      uses eventpb:TargetSysLog;
    }
  }
  // event/target.proto
  grouping TargetLog {
    leaf TargetLog_LogID {
      type uint64;
    }
    container TargetLog_Ts {
      uses protobufpb:Timestamp;
    }
    leaf TargetLog_LoggingType {
      type eventpb:LoggingTypeOptions;
    }
    leaf TargetLog_LoggingSeverityType {
      type eventpb:LoggingSeverityTypeOptions;
    }
    leaf TargetLog_Message {
      type string;
    }
    container TargetLog_Param {
      uses eventpb:TargetLogOptionalParameter;
    }
    container TargetLog_Internal {
      uses eventpb:Internal;
    }
  }
}
