module test-anyxml {
  prefix test-anyxml;
  namespace "http://yuma123.org/ns/test/netconfd/anyxml/test-anyxml";

  container c {
    anyxml a;
  }

  rpc ping-pong {
    input {
      anyxml ping;
    }
    output {
      anyxml pong;
    }
  }
}
