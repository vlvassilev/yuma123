submodule test1a {

    belongs-to test1 { prefix t1a; }

    revision 2008-10-12 {
        description "Initial revision.";
    }

    typedef X { type int32 { range 1..10; } }

    typedef XX { type int32 { range min..10; } }

    list test1-a.sub { 
       key "a b c";

       leaf a { type int32; }
       leaf b { type int16; }
       leaf c { type int64; }
       choice d {
         case e {
           leaf f { type empty; }
           leaf g { type int32; mandatory true; }
           leaf h { type int32; config false; }
         }
         leaf i { type leafref { path ../../../a; } }
         leaf j { type t1a:X; }
       }
    }

}
