module test5 {

    namespace "urn:ietf:params:xml:ns:yang:test5";
    prefix "t5";

    revision 2008-11-20 {
        description "Initial revision.";
    }

    container test5 {
      list a {
        key g1;
        leaf g1 { type string; }
        leaf g2 { type string; }
      }
   }
}
