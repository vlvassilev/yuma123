module intri-cli {

  namespace "intri:intri-cli";
  prefix "intri-cli";
  organization "
    Intrising Inc.";
  contact "
    intrising@intrising.com.tw";
  revision 2022-06-24 {
    description "Build date.";
  }

  import intri-empty {
    prefix intri-empty;
  }
  grouping ScriptAction {
    leaf Token {
      mandatory "true";
      type string;
    }
    leaf FileURL {
      mandatory "true";
      type string;
    }
    leaf IsFTPS {
      mandatory "true";
      type boolean;
    }
    leaf ForceTFTP {
      mandatory "true";
      type boolean;
    }
  }
  rpc intri-cli-CLI-RunScript {
    input {
      uses ScriptAction;
    }
  }
}
