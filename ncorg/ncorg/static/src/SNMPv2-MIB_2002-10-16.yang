/*
 * This module has been generated by smidump 0.4.6:
 *
 *      smidump -f yang --yang-smi-extensions SNMPv2-MIB
 *
 * Do not edit. Edit the source file instead!
 */

module SNMPv2-MIB {

   /*** NAMESPACE / PREFIX DEFINITION ***/

   namespace "urn:ietf:params:xml:ns:yang:smiv2:SNMPv2-MIB";
   prefix "snmpv2-mib";

   /*** LINKAGE (IMPORTS / INCLUDES) ***/

   import SNMPv2-TC  { prefix "smiv2"; }
   import yang-smi   { prefix "smi"; }
   import yang-types { prefix "yang"; }

   /*** META INFORMATION ***/

   organization     
     "IETF SNMPv3 Working Group";

   contact          
     "WG-EMail:   snmpv3@lists.tislabs.com
      Subscribe:  snmpv3-request@lists.tislabs.com
      
      Co-Chair:   Russ Mundy
                  Network Associates Laboratories
      postal:     15204 Omega Drive, Suite 300
                  Rockville, MD 20850-4601
                  USA
      EMail:      mundy@tislabs.com
      phone:      +1 301 947-7107
      
      Co-Chair:   David Harrington
                  Enterasys Networks
      postal:     35 Industrial Way
                  P. O. Box 5005
                  Rochester, NH 03866-5005
                  USA
      EMail:      dbh@enterasys.com
      phone:      +1 603 337-2614
      
      Editor:     Randy Presuhn
                  BMC Software, Inc.
      postal:     2141 North First Street
                  San Jose, CA 95131
                  USA
      EMail:      randy_presuhn@bmc.com
      phone:      +1 408 546-1006";

   description      
     "The MIB module for SNMP entities.
      
      Copyright (C) The Internet Society (2002). This
      version of this MIB module is part of RFC 3418;
      see the RFC itself for full legal notices.";

   revision "2002-10-16" {
      description   
        "This revision of this MIB module was published as
         RFC 3418.";
   }
   revision "1995-11-09" {
      description   
        "This revision of this MIB module was published as
         RFC 1907.";
   }
   revision "1993-04-01" {
      description   
        "The initial revision of this MIB module was published
         as RFC 1450.";
   }

   container system {

      leaf sysDescr {
         type smiv2:DisplayString {
            length "0..255";
         }
         config false;
         description 
           "A textual description of the entity.  This value should
            include the full name and version identification of
            the system's hardware type, software operating-system,
            and networking software.";
         smi:oid "1.3.6.1.2.1.1.1";
      }

      leaf sysObjectID {
         type yang:object-identifier;
         config false;
         description 
           "The vendor's authoritative identification of the
            network management subsystem contained in the entity.
            This value is allocated within the SMI enterprises
            subtree (1.3.6.1.4.1) and provides an easy and
            unambiguous means for determining `what kind of box' is
            being managed.  For example, if vendor `Flintstones,
            Inc.' was assigned the subtree 1.3.6.1.4.1.424242,
            it could assign the identifier 1.3.6.1.4.1.424242.1.1
            to its `Fred Router'.";
         smi:oid "1.3.6.1.2.1.1.2";
      }

      leaf sysUpTime {
         type yang:timeticks;
         config false;
         description 
           "The time (in hundredths of a second) since the
            network management portion of the system was last
            re-initialized.";
         smi:oid "1.3.6.1.2.1.1.3";
      }

      leaf sysContact {
         type smiv2:DisplayString {
            length "0..255";
         }
         config true;
         description 
           "The textual identification of the contact person for
            this managed node, together with information on how
            to contact this person.  If no contact information is
            known, the value is the zero-length string.";
         smi:oid "1.3.6.1.2.1.1.4";
      }

      leaf sysName {
         type smiv2:DisplayString {
            length "0..255";
         }
         config true;
         description 
           "An administratively-assigned name for this managed
            node.  By convention, this is the node's fully-qualified
            domain name.  If the name is unknown, the value is
            the zero-length string.";
         smi:oid "1.3.6.1.2.1.1.5";
      }

      leaf sysLocation {
         type smiv2:DisplayString {
            length "0..255";
         }
         config true;
         description 
           "The physical location of this node (e.g., 'telephone
            closet, 3rd floor').  If the location is unknown, the
            value is the zero-length string.";
         smi:oid "1.3.6.1.2.1.1.6";
      }

      leaf sysServices {
         type int32 {
            range "0..127";
         }
         config false;
         description 
           "A value which indicates the set of services that this
            entity may potentially offer.  The value is a sum.
            
            This sum initially takes the value zero. Then, for
            each layer, L, in the range 1 through 7, that this node
            performs transactions for, 2 raised to (L - 1) is added
            to the sum.  For example, a node which performs only
            routing functions would have a value of 4 (2^(3-1)).
            In contrast, a node which is a host offering application
            services would have a value of 72 (2^(4-1) + 2^(7-1)).
            Note that in the context of the Internet suite of
            protocols, values should be calculated accordingly:
            
                 layer      functionality
                   1        physical (e.g., repeaters)
                   2        datalink/subnetwork (e.g., bridges)
                   3        internet (e.g., supports the IP)
                   4        end-to-end  (e.g., supports the TCP)
                   7        applications (e.g., supports the SMTP)
            
            For systems including OSI protocols, layers 5 and 6
            may also be counted.";
         smi:oid "1.3.6.1.2.1.1.7";
      }

      leaf sysORLastChange {
         type yang:timestamp;
         config false;
         description 
           "The value of sysUpTime at the time of the most recent
            change in state or value of any instance of sysORID.";
         smi:oid "1.3.6.1.2.1.1.8";
      }


      /* XXX table comments here XXX */

      list sysOREntry {

         key "sysORIndex";
         description 
           "An entry (conceptual row) in the sysORTable.";
         smi:oid "1.3.6.1.2.1.1.9.1";


         leaf sysORIndex {
            type int32 {
               range "1..2147483647";
            }
            config false;
            description   
              "The auxiliary variable used for identifying instances
               of the columnar objects in the sysORTable.";
            smi:oid "1.3.6.1.2.1.1.9.1.1";
         }

         leaf sysORID {
            type yang:object-identifier;
            config false;
            description   
              "An authoritative identification of a capabilities
               statement with respect to various MIB modules supported
               by the local SNMP application acting as a command
               responder.";
            smi:oid "1.3.6.1.2.1.1.9.1.2";
         }

         leaf sysORDescr {
            type smiv2:DisplayString;
            config false;
            description   
              "A textual description of the capabilities identified
               by the corresponding instance of sysORID.";
            smi:oid "1.3.6.1.2.1.1.9.1.3";
         }

         leaf sysORUpTime {
            type yang:timestamp;
            config false;
            description   
              "The value of sysUpTime at the time this conceptual
               row was last instantiated.";
            smi:oid "1.3.6.1.2.1.1.9.1.4";
         }
      }
      smi:oid "1.3.6.1.2.1.1";
   }

   container snmp {

      leaf snmpInPkts {
         type yang:counter32;
         config false;
         description 
           "The total number of messages delivered to the SNMP
            entity from the transport service.";
         smi:oid "1.3.6.1.2.1.11.1";
      }

      leaf snmpOutPkts {
         type yang:counter32;
         config false;
         status obsolete;
         description 
           "The total number of SNMP Messages which were
            passed from the SNMP protocol entity to the
            transport service.";
         smi:oid "1.3.6.1.2.1.11.2";
      }

      leaf snmpInBadVersions {
         type yang:counter32;
         config false;
         description 
           "The total number of SNMP messages which were delivered
            to the SNMP entity and were for an unsupported SNMP
            version.";
         smi:oid "1.3.6.1.2.1.11.3";
      }

      leaf snmpInBadCommunityNames {
         type yang:counter32;
         config false;
         description 
           "The total number of community-based SNMP messages (for
            example,  SNMPv1) delivered to the SNMP entity which
            used an SNMP community name not known to said entity.
            Also, implementations which authenticate community-based
            SNMP messages using check(s) in addition to matching
            the community name (for example, by also checking
            whether the message originated from a transport address
            allowed to use a specified community name) MAY include
            in this value the number of messages which failed the
            additional check(s).  It is strongly RECOMMENDED that
            
            the documentation for any security model which is used
            to authenticate community-based SNMP messages specify
            the precise conditions that contribute to this value.";
         smi:oid "1.3.6.1.2.1.11.4";
      }

      leaf snmpInBadCommunityUses {
         type yang:counter32;
         config false;
         description 
           "The total number of community-based SNMP messages (for
            example, SNMPv1) delivered to the SNMP entity which
            represented an SNMP operation that was not allowed for
            the SNMP community named in the message.  The precise
            conditions under which this counter is incremented
            (if at all) depend on how the SNMP entity implements
            its access control mechanism and how its applications
            interact with that access control mechanism.  It is
            strongly RECOMMENDED that the documentation for any
            access control mechanism which is used to control access
            to and visibility of MIB instrumentation specify the
            precise conditions that contribute to this value.";
         smi:oid "1.3.6.1.2.1.11.5";
      }

      leaf snmpInASNParseErrs {
         type yang:counter32;
         config false;
         description 
           "The total number of ASN.1 or BER errors encountered by
            the SNMP entity when decoding received SNMP messages.";
         smi:oid "1.3.6.1.2.1.11.6";
      }

      leaf snmpInTooBigs {
         type yang:counter32;
         config false;
         status obsolete;
         description 
           "The total number of SNMP PDUs which were
            delivered to the SNMP protocol entity and for
            which the value of the error-status field was
            `tooBig'.";
         smi:oid "1.3.6.1.2.1.11.8";
      }

      leaf snmpInNoSuchNames {
         type yang:counter32;
         config false;
         status obsolete;
         description 
           "The total number of SNMP PDUs which were
            delivered to the SNMP protocol entity and for
            which the value of the error-status field was
            `noSuchName'.";
         smi:oid "1.3.6.1.2.1.11.9";
      }

      leaf snmpInBadValues {
         type yang:counter32;
         config false;
         status obsolete;
         description 
           "The total number of SNMP PDUs which were
            delivered to the SNMP protocol entity and for
            which the value of the error-status field was
            `badValue'.";
         smi:oid "1.3.6.1.2.1.11.10";
      }

      leaf snmpInReadOnlys {
         type yang:counter32;
         config false;
         status obsolete;
         description 
           "The total number valid SNMP PDUs which were delivered
            to the SNMP protocol entity and for which the value
            of the error-status field was `readOnly'.  It should
            be noted that it is a protocol error to generate an
            SNMP PDU which contains the value `readOnly' in the
            error-status field, as such this object is provided
            as a means of detecting incorrect implementations of
            the SNMP.";
         smi:oid "1.3.6.1.2.1.11.11";
      }

      leaf snmpInGenErrs {
         type yang:counter32;
         config false;
         status obsolete;
         description 
           "The total number of SNMP PDUs which were delivered
            to the SNMP protocol entity and for which the value
            of the error-status field was `genErr'.";
         smi:oid "1.3.6.1.2.1.11.12";
      }

      leaf snmpInTotalReqVars {
         type yang:counter32;
         config false;
         status obsolete;
         description 
           "The total number of MIB objects which have been
            retrieved successfully by the SNMP protocol entity
            as the result of receiving valid SNMP Get-Request
            and Get-Next PDUs.";
         smi:oid "1.3.6.1.2.1.11.13";
      }

      leaf snmpInTotalSetVars {
         type yang:counter32;
         config false;
         status obsolete;
         description 
           "The total number of MIB objects which have been
            altered successfully by the SNMP protocol entity as
            the result of receiving valid SNMP Set-Request PDUs.";
         smi:oid "1.3.6.1.2.1.11.14";
      }

      leaf snmpInGetRequests {
         type yang:counter32;
         config false;
         status obsolete;
         description 
           "The total number of SNMP Get-Request PDUs which
            have been accepted and processed by the SNMP
            protocol entity.";
         smi:oid "1.3.6.1.2.1.11.15";
      }

      leaf snmpInGetNexts {
         type yang:counter32;
         config false;
         status obsolete;
         description 
           "The total number of SNMP Get-Next PDUs which have been
            accepted and processed by the SNMP protocol entity.";
         smi:oid "1.3.6.1.2.1.11.16";
      }

      leaf snmpInSetRequests {
         type yang:counter32;
         config false;
         status obsolete;
         description 
           "The total number of SNMP Set-Request PDUs which
            have been accepted and processed by the SNMP protocol
            entity.";
         smi:oid "1.3.6.1.2.1.11.17";
      }

      leaf snmpInGetResponses {
         type yang:counter32;
         config false;
         status obsolete;
         description 
           "The total number of SNMP Get-Response PDUs which
            have been accepted and processed by the SNMP protocol
            entity.";
         smi:oid "1.3.6.1.2.1.11.18";
      }

      leaf snmpInTraps {
         type yang:counter32;
         config false;
         status obsolete;
         description 
           "The total number of SNMP Trap PDUs which have been
            accepted and processed by the SNMP protocol entity.";
         smi:oid "1.3.6.1.2.1.11.19";
      }

      leaf snmpOutTooBigs {
         type yang:counter32;
         config false;
         status obsolete;
         description 
           "The total number of SNMP PDUs which were generated
            by the SNMP protocol entity and for which the value
            of the error-status field was `tooBig.'";
         smi:oid "1.3.6.1.2.1.11.20";
      }

      leaf snmpOutNoSuchNames {
         type yang:counter32;
         config false;
         status obsolete;
         description 
           "The total number of SNMP PDUs which were generated
            by the SNMP protocol entity and for which the value
            of the error-status was `noSuchName'.";
         smi:oid "1.3.6.1.2.1.11.21";
      }

      leaf snmpOutBadValues {
         type yang:counter32;
         config false;
         status obsolete;
         description 
           "The total number of SNMP PDUs which were generated
            by the SNMP protocol entity and for which the value
            of the error-status field was `badValue'.";
         smi:oid "1.3.6.1.2.1.11.22";
      }

      leaf snmpOutGenErrs {
         type yang:counter32;
         config false;
         status obsolete;
         description 
           "The total number of SNMP PDUs which were generated
            by the SNMP protocol entity and for which the value
            of the error-status field was `genErr'.";
         smi:oid "1.3.6.1.2.1.11.24";
      }

      leaf snmpOutGetRequests {
         type yang:counter32;
         config false;
         status obsolete;
         description 
           "The total number of SNMP Get-Request PDUs which
            have been generated by the SNMP protocol entity.";
         smi:oid "1.3.6.1.2.1.11.25";
      }

      leaf snmpOutGetNexts {
         type yang:counter32;
         config false;
         status obsolete;
         description 
           "The total number of SNMP Get-Next PDUs which have
            been generated by the SNMP protocol entity.";
         smi:oid "1.3.6.1.2.1.11.26";
      }

      leaf snmpOutSetRequests {
         type yang:counter32;
         config false;
         status obsolete;
         description 
           "The total number of SNMP Set-Request PDUs which
            have been generated by the SNMP protocol entity.";
         smi:oid "1.3.6.1.2.1.11.27";
      }

      leaf snmpOutGetResponses {
         type yang:counter32;
         config false;
         status obsolete;
         description 
           "The total number of SNMP Get-Response PDUs which
            have been generated by the SNMP protocol entity.";
         smi:oid "1.3.6.1.2.1.11.28";
      }

      leaf snmpOutTraps {
         type yang:counter32;
         config false;
         status obsolete;
         description 
           "The total number of SNMP Trap PDUs which have
            been generated by the SNMP protocol entity.";
         smi:oid "1.3.6.1.2.1.11.29";
      }

      leaf snmpEnableAuthenTraps {
         type enumeration {
            enum enabled  { value 1; }
            enum disabled { value 2; }
         }
         config true;
         description 
           "Indicates whether the SNMP entity is permitted to
            generate authenticationFailure traps.  The value of this
            object overrides any configuration information; as such,
            it provides a means whereby all authenticationFailure
            traps may be disabled.
            
            Note that it is strongly recommended that this object
            be stored in non-volatile memory so that it remains
            constant across re-initializations of the network
            management system.";
         smi:oid "1.3.6.1.2.1.11.30";
      }

      leaf snmpSilentDrops {
         type yang:counter32;
         config false;
         description 
           "The total number of Confirmed Class PDUs (such as
            GetRequest-PDUs, GetNextRequest-PDUs,
            GetBulkRequest-PDUs, SetRequest-PDUs, and
            InformRequest-PDUs) delivered to the SNMP entity which
            were silently dropped because the size of a reply
            containing an alternate Response Class PDU (such as a
            Response-PDU) with an empty variable-bindings field
            was greater than either a local constraint or the
            maximum message size associated with the originator of
            the request.";
         smi:oid "1.3.6.1.2.1.11.31";
      }

      leaf snmpProxyDrops {
         type yang:counter32;
         config false;
         description 
           "The total number of Confirmed Class PDUs
            (such as GetRequest-PDUs, GetNextRequest-PDUs,
            GetBulkRequest-PDUs, SetRequest-PDUs, and
            InformRequest-PDUs) delivered to the SNMP entity which
            were silently dropped because the transmission of
            the (possibly translated) message to a proxy target
            failed in a manner (other than a time-out) such that
            no Response Class PDU (such as a Response-PDU) could
            be returned.";
         smi:oid "1.3.6.1.2.1.11.32";
      }
      smi:oid "1.3.6.1.2.1.11";
   }

   container snmpTrap {

      leaf snmpTrapOID {
         type yang:object-identifier;
         config false;
         description 
           "The authoritative identification of the notification
            currently being sent.  This variable occurs as
            the second varbind in every SNMPv2-Trap-PDU and
            InformRequest-PDU.";
         smi:oid "1.3.6.1.6.3.1.1.4.1";
      }

      leaf snmpTrapEnterprise {
         type yang:object-identifier;
         config false;
         description 
           "The authoritative identification of the enterprise
            associated with the trap currently being sent.  When an
            SNMP proxy agent is mapping an RFC1157 Trap-PDU
            into a SNMPv2-Trap-PDU, this variable occurs as the
            last varbind.";
         smi:oid "1.3.6.1.6.3.1.1.4.3";
      }
      smi:oid "1.3.6.1.6.3.1.1.4";
   }

   container snmpSet {

      leaf snmpSetSerialNo {
         type smiv2:TestAndIncr;
         config true;
         description 
           "An advisory lock used to allow several cooperating
            command generator applications to coordinate their
            use of the SNMP set operation.
            
            This object is used for coarse-grain coordination.
            To achieve fine-grain coordination, one or more similar
            objects might be defined within each MIB group, as
            appropriate.";
         smi:oid "1.3.6.1.6.3.1.1.6.1";
      }
      smi:oid "1.3.6.1.6.3.1.1.6";
   }

   notification coldStart {
      description   
        "A coldStart trap signifies that the SNMP entity,
         supporting a notification originator application, is
         reinitializing itself and that its configuration may
         have been altered.";
      smi:oid "1.3.6.1.6.3.1.1.5.1";

   }

   notification warmStart {
      description   
        "A warmStart trap signifies that the SNMP entity,
         supporting a notification originator application,
         is reinitializing itself such that its configuration
         is unaltered.";
      smi:oid "1.3.6.1.6.3.1.1.5.2";

   }

   notification authenticationFailure {
      description   
        "An authenticationFailure trap signifies that the SNMP
         entity has received a protocol message that is not
         properly authenticated.  While all implementations
         of SNMP entities MAY be capable of generating this
         trap, the snmpEnableAuthenTraps object indicates
         whether this trap will be generated.";
      smi:oid "1.3.6.1.6.3.1.1.5.5";

   }
} /* end of module SNMPv2-MIB */
