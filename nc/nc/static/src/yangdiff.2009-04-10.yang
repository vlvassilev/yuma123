module yangdiff {

    yang-version 1;
    namespace "http://netconfcentral.com/ns/yangdiff";
    prefix ydi;

    import ncxtypes { prefix nt; }

    import ncx { prefix ncx; }

    import ncx-app-common { prefix ncxapp; }

    organization "Netconf Central";

    contact
        "Andy Bierman <andy at netconfcentral.com>";

    description 
       "yangdiff compares the semantics and syntax between 
        two revisions of the same YANG module.  The 
        conceptual data model is compared, not the 
        individual files.  

        For example, unless statement order is significant,
        changing the order is not considered a change, and 
        is not reported.  Reformatted test (whitespace changes)
        are also not reported.

        If a data type definition is changed in form,
        but not content, then a 'modify type' message
        will be generated, but no additional sub-fields
        will be reported.

        INPUT FILES

           To compare one module, use the 'old' and 'new'
           parameters to specify YANG module files,
           each with a filespec string ending with the '.yang'
           file extension.  The filespecs must represent
           different files.  If the 'old' parameter represents
           a directory, then this directory will be searched
           for the 'new' filename.

           To compare all the modules in a subtree, use the 
           'old' and 'new' parameters to specify a directory
           to be searched for YANG modules to be processed.
           In this mode, each new module is compared to
           a corresponding file within the 'old' subtree.
           Also, dependency and include files
           will be kept separate, for each subtree.
           
           Unless the 'help' or 'version' parameters is entered, 
           the 'old' and 'new' parameters must be present.

        SEARCH PATH

            When a module name is entered as input, or when a
            module or submodule name is specified in an import or include
            statement within the file, the following search algorithm
            is used to find the file:

            1) if the parameter for the file that generated the
               search request represents a subtree, search that
               subtree first.
            2) file is in the current directory
            3) YANG_MODPATH environment var (or set by modpath parameter)
            4) $HOME/modules directory
            5) $YANG_HOME/modules directory
            6) $YANG_INSTALL/modules directory OR
               default install module location, '/usr/share/yang/modules'

            By default, the entire directory tree for all locations
            (except step 1) will be searched, not just the specified
            directory.  The 'no-subdirs' parameter can be used to
            prevent sub-directories from being searched.

            Any directory name beginning with a dot character '.'
            will be skipped.  Also, any directory named 'CVS' will
            be skipped in directory searches.

        OUTPUT MODES

            By default, any comparison output will be sent to STDOUT.

            The 'output' parameter can be used to specify the 
            full filespec of the output file,  or a
            complete directory specification to be combined
            with the default filename (yangdiff.log).

        ERROR LOGGING

            By default, warnings and errors are sent to STDOUT.

            A log file can be specified instead with the 'log' parameter.
            Existing log files can be reused with the 'logappend'
            parameter, otherwise log files are overwritten.

            The logging level can be controlled with the 'log-level'
            parameter.  The default log level is 'info'.  The
            log-levels are additive:

               off:    suppress all errors (not recommended!)
                       A program return code of '1' indicates some error.
               error:  print errors
               warn:   print warnings
               info:   print generally interesting trace info
               debug:  print general debugging trace info
               debug2: print verbose debugging trace info
    
        ENVIRONMENT VARIABLES

            The following optional environment variables can be used
            to control module and data search behavior:

            HOME:  the user's home directory  (e.g., /home/andy)

            YANG_HOME:  The root of the user's YANG work directory
                        (e.g., /home/andy/swdev/netconf)

            YANG_INSTALL:  The root of the directory that yangdiff
                            is installed on this system
                           (default is, /usr/share/yang)

            YANG_MODPATH: Colon-separated list of directories to
                          search for modules and submodules.
                          (e.g.: './workdir/modules:/home/andy/test-modules')
                          The 'modpath' parameter will override this
                          environment variable, if both are present.

       CONFIGURATION FILES

              * config file
                default: /etc/yangdiff.conf

            An ASCII configuration file format is supported to 
            store command line parameters.  The 'config' parameter
            is used to specify a specific config file, otherwise
            the default config file will be checked. 

            - A hash mark until EOLN is treated as a comment
            - All text is case-sensitive
            - Whitespace within a line is not significant
            - Whitespace to end a line is significant/
              Unless the line starts a multi-line string,
              an escaped EOLN (backslash EOLN) is needed
              to enter a leaf on multiple lines.
            - For parmsets that define lists, the key components
              are listed just after the parameter name, without
              any name,  e.g.,

                interface eth0 {
                  # name = eth0 is not listed inside the braces
                  ifMtu 1500
                  ifName mySystem
                }
 
            A config file can contain any number of parameter
            sets for different programs.  Each program
            must have its own section, identifies by its name:

                # this is a comment
                yangdiff {
                  log-level debug
                  output \"~/swdev/testfiles\"
                }
 
                yangdump {
                  ...
                }

        FILES            

            The following data files must be present in the module
            search path in order for this program to function:
 
              * yangdiff.ncx (this file)
                default locations: 
                  ~/modules/netconfcentral/yangdiff.ncx
                  /usr/share/yang/modules/netconfcentral/yangdiff.ncx

              * ncxtypes.ncx
                default locations: 
                   ~/modules/netconfcentral/ncxtypes.ncx
                   /usr/share/yang/modules/netconfcentral/ncxtypes.ncx

        BUGS
           - sub-modules ignored in directory processing mode,
             and module comparisons do not include sub-modules;
             the 'unified' parameter will be added later to
             support this feature
           - comparison does not examine beyond the current
             module (i.e. differences in imported modules);
             The exception are typedef chains, which are
             examined for semantic changes, regardless of
             module location of the typedef.
          
             Internal diagnostics may generate the following
             type of message if any bugs are detected at runtime:

             [E0]
                 filename.c:linenum error-number (error-msg)
 
             Please send a bug report to support@netconfcentral.com
             if any messages of this type appear in the error log.
        ";

    revision 2009-04-10 {
       description 
          "Moved common parameters to ncx-app-common";
    }

    revision 2008-08-17 {
       description 
          "Initial version";
    }

    typedef DiffType {
        description
          "Type of comparison output requested.";
        type enumeration {
            enum terse;
            enum normal;
            enum revision;
        }
        default "normal";
    }

    container yangdiff {
        ncx:cli;

        description 
           "CLI Parameter Set for the YANG Module Compare Application.";

        uses ncxapp:NcxAppCommon;

        leaf old {
            description 
              "The older of the two revisions to compare.

               If this parameter indicates a filename, then it
               represents the YANG source module name 
               to compare as the older of the two revisions.

               If this parameter indicates a directory,
               then it will be used to to search for a
               file with the same name as identified by
               the 'new' parameter.

               If this string begins with a '~' character,
               then a username is expected to follow or
               a directory separator character.  If it begins
               with a '$' character, then an environment variable
               name is expected to follow.

                  ~/some/path ==> <my-home-dir>/some/path

                  ~fred/some/path ==> <fred-home-dir>/some/path

                  $workdir/some/path ==> <workdir-env-var>/some/path

               This parameter must be present unless the 'help'
               or 'version' parameters are used.";
            type nt:NcModuleSpec;
        }

        leaf new {
            description 
              "If this parameter indicates a filename, then it
               represents the YANG source module name 
               to compare as the newer of the two revisions.

               If this parameter indicates a directory
               (and the 'old' parameter indicates a filename),
               then it will be used to to search for a
               file with the same name as the 'new' parameter.

               If the 'old' parameter identifies a directory
               as well (and the 'no-subdirs' parameter is present),
               then the modules within the 'new' directory will be 
               compared to files with the same name in the 'old' 
               directory.  If the 'no-subdirs' parameter is not
               present, then all sub-directories within the 'src'
               directory will also be checked.

               If this string begins with a '~' character,
               then a username is expected to follow or
               a directory separator character.  If it begins
               with a '$' character, then an environment variable
               name is expected to follow.

                  ~/some/path ==> <my-home-dir>/some/path

                  ~fred/some/path ==> <fred-home-dir>/some/path
 
                  $workdir/some/path ==> <workdir-env-var>/some/path

               This parameter must be present unless the 'help'
               or 'version' parameters are used.";
            type nt:NcModuleSpec;
        }

        leaf difftype {
            description 
              "The type of comparison output requested.
               Allowed values are 'terse', 'normal', and 'revision'.

               The basic format is:

                 [add/delete/modify] field-name [field-value]

              The 'terse' option will include the names
              of the top-level fields that are different.

                 A foo  -->  Added foo in new revision
                 D foo  -->  Deleted foo in new revision
                 M foo  -->  Modified foo in new revision (value too long)
                 M foo from '0' to '1'  -->  Modified foo in new revision

             The 'normal' option will also include any changes
             for any nested fields or objects.  This is the default
             option.

             The 'revision' option will generate the differences report
             in YANG revision-stmt format.  For example:

              revision <todays-date> {
                description 
                  \"
                    - Added import baxtypes
                    - Changed contact to 'support@acme.com'
                    - Modified container myobjects
                       - Added list first-list\";
              } ";
            type DiffType;
        }

        leaf output {
          description 
            "Output directory or file name to use. 
             The default is STDOUT if none is specified.

             If this parameter represents an existing directory,
             then the default comparison output file (yangdiff.log)
             will be generated in the specified directory.

             If this parameter represents a file name,
             then all comparison output will be directed
             to the specified file.  If the file already exists,
             it will be overwritten.

             If this string begins with a '~' character,
             then a username is expected to follow or
             a directory separator character.  If it begins
             with a '$' character, then an environment variable
             name is expected to follow.

                ~/some/path ==> <my-home-dir>/some/path

                ~fred/some/path ==> <fred-home-dir>/some/path

                $workdir/some/path ==> <workdir-env-var>/some/path";

          type string;
        }

	leaf no-header {
          description
             "If present, the header clauses will be skipped, and any 
	      differences between the module headers will not be reported.
              Only object definitions will be compared.

              If missing, then header clauses will be compared,
              along will all the object definitions.";
          type empty;
        }

	leaf no-subdirs {
          description
             "If present, the file search paths for modules, scripts, and data
              files will not include sub-directories if they exist in the
              specified path.

              If missing, then these file search paths will include
              sub-directories, if present.  Any directory name beginning
              with a dot '.' character, or named 'CVS', will be ignored.";
          type empty;
        }
    }

}
