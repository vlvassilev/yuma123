submodule intri-timerange-enum {
  belongs-to "intri-timerange" {
    prefix "intri-timerange-enum";
  }
  revision 2022-06-14 {
    description "Build date.";
  }
  // core/timerange/timerange.proto
  typedef CommandTypeOptions {
    type enumeration {
      enum COMMAND_TYPE_PERIODIC {
        description "[Periodic]";
        value 0;
      }
      enum COMMAND_TYPE_ABSOLUTE {
        description "[Absolute]";
        value 1;
      }
    }
  }
  // core/timerange/timerange.proto
  typedef PeriodicDayTypeOptions {
    type enumeration {
      enum PERIODIC_DAY_TYPE_DAYOFWEEK {
        description "[Day of the week]";
        value 0;
      }
      enum PERIODIC_DAY_TYPE_DAILY {
        description "[Daily]";
        value 1;
      }
      enum PERIODIC_DAY_TYPE_WEEKDAYS {
        description "[Weekdays]";
        value 2;
      }
      enum PERIODIC_DAY_TYPE_WEEKEND {
        description "[Weekend]";
        value 3;
      }
    }
  }
}
