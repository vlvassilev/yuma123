submodule intri-dhcp-enum {
  belongs-to "intri-dhcp" {
    prefix "intri-dhcp-enum";
  }
  revision 2022-06-14 {
    description "Build date.";
  }
  // core/dhcp/common.proto
  typedef RemoteIDSourceTypeOptions {
    type enumeration {
      enum REMOTE_ID_SOURCE_TYPE_HOSTNAME {
        description "[Hostname] Hostname of this switch";
        value 0;
      }
      enum REMOTE_ID_SOURCE_TYPE_MAC_ADDRESS {
        description "[MacAddress] MAC address of this switch";
        value 1;
      }
      enum REMOTE_ID_SOURCE_TYPE_SYS_NAME {
        description "[SysName] SNMP sysName of this switch";
        value 2;
      }
      enum REMOTE_ID_SOURCE_TYPE_USER_DEFINED {
        description "[User defined] A user defined string as defined in custom remote ID is used";
        value 3;
      }
      enum REMOTE_ID_SOURCE_TYPE_PORT_ALIAS {
        description "[Port alias] The port alias value of the incoming port is used";
        value 4;
      }
    }
  }
  // core/dhcp/common.proto
  typedef CircuitIDSourceTypeOptions {
    type enumeration {
      enum CIRCUIT_ID_SOURCE_TYPE_PORT_ALIAS {
        description "[Port alias] Use port alias as the circuit ID";
        value 0;
      }
      enum CIRCUIT_ID_SOURCE_TYPE_IP_PORT_VLAN {
        description "[IP-Port-VLAN] Use the format {IP}-{port}-{VLANID} as the circuit ID";
        value 1;
      }
    }
  }
  // core/dhcp/common.proto
  typedef SnoopingPortDHCPFilteringTypeOptions {
    type enumeration {
      enum SNOOPING_PORT_DHCP_FILTERING_TYPE_DISABLED {
        description "[Disabled] DHCP frames are not removed";
        value 0;
      }
      enum SNOOPING_PORT_DHCP_FILTERING_TYPE_DROP_AND_EVENT {
        description "[Drop and event] DHCP response frames incoming from a user port are removed and a PACKET_INTERCEPTED event is send";
        value 1;
      }
      enum SNOOPING_PORT_DHCP_FILTERING_BLOCK_AND_EVENT {
        description "[Block and event] Port is blocked when an DHCP response incoming from a user port is detected. Needs operator intervention to unblock. Also a PACKET_INTERCEPTED event is send.";
        value 2;
      }
    }
  }
  // core/dhcp/common.proto
  typedef SnoopingPortSnoopingTrustTypeOptions {
    type enumeration {
      enum SNOOPING_PORT_SNOOPING_TYPE_TRUST_UNTRUSTED {
        description "[Untrusted] This port is untrusted and DHCP filtering applies";
        value 0;
      }
      enum SNOOPING_PORT_SNOOPING_TYPE_TRUST_TRUSTED {
        description "[Trusted] This port is trusted and no filtering occurs. Use when a DHCP server should be permitted on a local access port";
        value 1;
      }
    }
  }
  // core/dhcp/common.proto
  typedef SnoopingLastDropReasonTypeOptions {
    type enumeration {
      enum SNOOPING_LAST_DROP_REASON_TYPE_OK {
        description "[Ok] The packet is normal and will be forwarded";
        value 0;
      }
      enum SNOOPING_LAST_DROP_REASON_TYPE_ILLEGAL_DHCP_SERVER {
        description "[Illegal DHCP Server] Forbidden DHCP message on untrusted port";
        value 1;
      }
      enum SNOOPING_LAST_DROP_REASON_TYPE_DHCP_SERVER_SPOOFED {
        description "[DHCP Server Sproofed] Source MAC and DHCP client MAC did not match";
        value 2;
      }
      enum SNOOPING_LAST_DROP_REASON_TYPE_ILLEGAL_RELAY_AGENT {
        description "[DHCP Illegal Relay Agent]";
        value 3;
      }
      enum SNOOPING_LAST_DROP_REASON_TYPE_BINDING_MISMATCH {
        description "[DHCP Binding mismatch] DHCPRELEASE or DHCPDECLINE interface information did not match the binding table information";
        value 4;
      }
      enum SNOOPING_LAST_DROP_REASON_TYPE_FLOODING {
        description "[Flooding] Too many DHCP messages which appears to be an attack.";
        value 5;
      }
      enum SNOOPING_LAST_DROP_REASON_TYPE_DHCP_FILTERING {
        description "[DHCP Filtering] DHCP reponse is dropped by DHCP Filtering";
        value 6;
      }
    }
  }
  // core/dhcp/common.proto
  typedef ARPInspectionDatabaseTypeOptions {
    type enumeration {
      enum ARP_INSPECTION_DATABASE_TYPE_NONE {
        description "[None] Don't use any database";
        value 0;
      }
      enum ARP_INSPECTION_DATABASE_TYPE_DHCP {
        description "[DHCP] Use the DHCP snooping binding database as the arp inspection database";
        value 1;
      }
      enum ARP_INSPECTION_DATABASE_TYPE_ARP_ACL {
        description "[ACL] Use the ACL list as the arp inspection database";
        value 2;
      }
      enum ARP_INSPECTION_DATABASE_TYPE_BOTH {
        description "[Both] Use both DHCP and ACL";
        value 3;
      }
    }
  }
  // core/dhcp/common.proto
  typedef ARPInspectionACLRuleUnmatchedActionTypeOptions {
    type enumeration {
      enum ARP_INSPECTION_ACL_RULE_UNMATCHED_ACTION_TYPE_DENY {
        description "[Deny] The packet will be denied";
        value 0;
      }
      enum ARP_INSPECTION_ACL_RULE_UNMATCHED_ACTION_TYPE_PERMIT {
        description "[Permit] The packet will be passed";
        value 1;
      }
    }
  }
  // core/dhcp/common.proto
  typedef ARPInspectionACLRuleModeTypeOptions {
    type enumeration {
      enum ARP_INSPECTION_RULE_MODE_TYPE_UNUSED {
        description "[Unused] The ACL rule entry won't use this rule";
        value 0;
      }
      enum ARP_INSPECTION_RULE_MODE_TYPE_PERMIT {
        description "[Permit] The ACL rule entry will permit the packet if this mode is permitted";
        value 1;
      }
      enum ARP_INSPECTION_RULE_MODE_TYPE_DENY {
        description "[Deny] The ACL rule entry will deny the packet if this mode is denied";
        value 2;
      }
    }
  }
}
