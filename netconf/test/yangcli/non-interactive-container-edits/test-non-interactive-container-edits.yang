module test-non-interactive-container-edits {

  namespace "http://yuma123.org/ns/test-non-interactive-container-edits";
  prefix tnice;
  
  import ietf-interfaces { prefix if; }
  import mod2 { prefix m2; }

  organization  "yuma123.org";
  
  description "Model for testing yangcli non-interactive container edits. e.g.
      create /interfaces/interface -- name=eth1 type=ethernetCsmacd a/foo=hello b[key1='one'][key2='two']/bar=world
      create /interfaces/interface[name='eth1']/c -- c1/bar=world
      create /interfaces/interface -- name=eth2 type=ethernetCsmacd d b[key1='one'][key2='two']/bar=world";
  
  revision 2018-10-06 {
    description
      "Added presence container 'd' to expose bug entering
       valueless containers as parameter.";
  }

  augment "/if:interfaces/if:interface" {
    container a {
        leaf foo {
            type string;
        }
    }
    list b {
        key "key1 key2";
        leaf key1 {
            type string;
        }
        leaf key2 {
            type string;
        }
        leaf bar {      
            type string;
        }
    }
    uses m2:gr0;

    container d {
        presence "case with presence container parameter";
    }
  }
}
