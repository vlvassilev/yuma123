module intri-mirroring {

  namespace "intri:intri-mirroring";
  prefix "intri-mirroring";
  organization "
    Intrising Inc.";
  contact "
    intrising@intrising.com.tw";
  revision 2022-06-24 {
    description "Build date.";
  }

  import intri-device {
    prefix intri-device;
  }
  import intri-empty {
    prefix intri-empty;
  }
  import intri-common {
    prefix intri-common;
  }
  typedef DestinationTypeOptions {
    type enumeration {
      enum DESTINATION_TYPE_LOCAL {
        description "[Local] to set SPAN(Local Switched Port Analyzer) destination port interface";
        value 0;
      }
      enum DESTINATION_TYPE_REMOTE {
        description "[Remote] to set RSPAN(Remote SPAN) VLAN";
        value 1;
      }
    }
  }
  typedef SourceInterfaceTypeOptions {
    type enumeration {
      enum SOURCE_INTERFACE_TYPE_LOCAL {
        description "[Local] to set SPAN(Local Switched Port Analyzer) source port interface";
        value 0;
      }
      enum SOURCE_INTERFACE_TYPE_VLAN {
        description "*[Internal] to set source port interface";
        value 1;
      }
      enum SOURCE_INTERFACE_TYPE_REMOTE {
        description "[Remote] to set RSPAN(Remote SPAN) VLAN";
        value 2;
      }
    }
  }
  typedef DirectionTypeOptions {
    type enumeration {
      enum MIRRORING_DIRECTION_TYPE_NONE {
        description "[None] to disable mirroring direction";
        value 0;
      }
      enum MIRRORING_DIRECTION_TYPE_TX_ONLY {
        description "[TX only] to set mirroring direction TX only";
        value 1;
      }
      enum MIRRORING_DIRECTION_TYPE_RX_ONLY {
        description "[RX only] to set mirroring direction RX only";
        value 2;
      }
      enum MIRRORING_DIRECTION_TYPE_BOTH {
        description "[TX+RX] to set mirroring direction TX and RX both";
        value 3;
      }
    }
  }
  grouping Config {
    container RSPAN {
      uses RSPANConfig;
    }
    container DestinationList {
      uses DestinationSession;
    }
    container SourceList {
      uses SourceSession;
    }
  }
  grouping DestinationSessionEntry {
    leaf Index {
      mandatory "true";
      type int32;
    }
    leaf Type {
      mandatory "true";
      type DestinationTypeOptions;
    }
    container IdentifyNo {
      uses intri-device:InterfaceIdentify;
    }
  }
  grouping DestinationSession {
    container List {
      list List_Entry {
        uses DestinationSessionEntry;
      }
    }
  }
  grouping SourceSessionEntry {
    leaf DestinationIndex {
      mandatory "true";
      type int32;
    }
    leaf SourceInterface {
      mandatory "true";
      type SourceInterfaceTypeOptions;
    }
    container IdentifyNo {
      uses intri-device:InterfaceIdentify;
    }
    leaf DirectionType {
      mandatory "true";
      type DirectionTypeOptions;
    }
  }
  grouping SourceSession {
    container List {
      list List_Entry {
        uses SourceSessionEntry;
      }
    }
  }
  grouping RSPANConfig {
    leaf Enabled {
      mandatory "true";
      type boolean;
    }
    leaf VlanID {
      mandatory "true";
      type int32;
    }
  }
  rpc intri-mirroring-Mirroring-GetConfig {
    output {
      uses Config;
    }
  }
  rpc intri-mirroring-Mirroring-GetRSPAN {
    output {
      uses RSPANConfig;
    }
  }
  rpc intri-mirroring-Mirroring-SetRSPAN {
    input {
      uses RSPANConfig;
    }
  }
  rpc intri-mirroring-Mirroring-GetDestinationList {
    output {
      uses DestinationSession;
    }
  }
  rpc intri-mirroring-Mirroring-AddDestination {
    input {
      uses DestinationSessionEntry;
    }
  }
  rpc intri-mirroring-Mirroring-DeleteDestination {
    input {
      uses intri-common:Index;
    }
  }
  rpc intri-mirroring-Mirroring-UpdateDestination {
    input {
      uses DestinationSessionEntry;
    }
  }
  rpc intri-mirroring-Mirroring-GetSourceList {
    output {
      uses SourceSession;
    }
  }
  rpc intri-mirroring-Mirroring-AddSource {
    input {
      uses SourceSessionEntry;
    }
  }
  rpc intri-mirroring-Mirroring-DeleteSource {
    input {
      uses SourceSessionEntry;
    }
  }
  rpc intri-mirroring-Mirroring-UpdateSource {
    input {
      uses SourceSessionEntry;
    }
  }
}
