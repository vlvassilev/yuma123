module intri-poe {

  namespace "intri:intri-poe";
  prefix "intri-poe";
  organization "
    Intrising Inc.";
  contact "
    intrising@intrising.com.tw";
  revision 2022-06-24 {
    description "Build date.";
  }

  import intri-device {
    prefix intri-device;
  }
  import intri-hardware {
    prefix intri-hardware;
  }
  import intri-empty {
    prefix intri-empty;
  }
  typedef LLDPDeliverUsageTypeOptions {
    type enumeration {
      enum LLDP_L2_USAGE_TYPE_L1 {
        description "";
        value 0;
      }
      enum LLDP_L2_USAGE_TYPE_L1_AUTO {
        description "";
        value 1;
      }
      enum LLDP_L2_USAGE_TYPE_LLDP {
        description "";
        value 2;
      }
      enum LLDP_L2_USAGE_TYPE_LLDP_AUTO {
        description "";
        value 3;
      }
      enum LLDP_L2_USAGE_TYPE_CDP {
        description "";
        value 4;
      }
      enum LLDP_L2_USAGE_TYPE_CDP_AUTO {
        description "";
        value 5;
      }
    }
  }
  grouping Config {
    container Budget {
      uses SystemBudget;
    }
    container Port {
      uses PortConfig;
    }
  }
  grouping SystemBudget {
    leaf MaxPowerAvailable {
      mandatory "true";
      type int32;
    }
  }
  grouping PortConfig {
    container List {
      list List_Entry {
        uses ConfigEntry;
      }
    }
  }
  grouping ConfigEntry {
    container IdentifyNo {
      uses intri-device:InterfaceIdentify;
    }
    leaf Enabled {
      mandatory "true";
      type boolean;
    }
    leaf Mode {
      mandatory "true";
      type intri-hardware:PoEPortModeTypeOptions;
    }
    leaf Priority {
      mandatory "true";
      type intri-hardware:PoEPriorityLevelTypeOptions;
    }
  }
  grouping SystemStatus {
    leaf MinShutDownVoltage {
      mandatory "true";
      type decimal64 {
        fraction-digits 2;
      }
    }
    leaf MaxShutDownVoltage {
      mandatory "true";
      type decimal64 {
        fraction-digits 2;
      }
    }
    leaf VMainVoltage {
      mandatory "true";
      type decimal64 {
        fraction-digits 2;
      }
    }
    leaf IMainCurrent {
      mandatory "true";
      type decimal64 {
        fraction-digits 2;
      }
    }
    leaf PowerConsumption {
      mandatory "true";
      type decimal64 {
        fraction-digits 2;
      }
    }
  }
  grouping PortStatus {
    container List {
      list List_Entry {
        uses PortStatusEntry;
      }
    }
  }
  grouping PortStatusEntry {
    container IdentifyNo {
      uses intri-device:InterfaceIdentify;
    }
    leaf Condition {
      mandatory "true";
      type intri-hardware:PoEConditionTypeOptions;
    }
    leaf DeterminedClass {
      mandatory "true";
      type intri-hardware:PoEDeterminedClassTypeOptions;
    }
    leaf Priority {
      mandatory "true";
      type intri-hardware:PoEPriorityLevelTypeOptions;
    }
    leaf OutputCurrent {
      mandatory "true";
      type decimal64 {
        fraction-digits 2;
      }
    }
    leaf OutputVoltage {
      mandatory "true";
      type decimal64 {
        fraction-digits 2;
      }
    }
    leaf OutputPower {
      mandatory "true";
      type decimal64 {
        fraction-digits 2;
      }
    }
    leaf SupportMaxPower {
      mandatory "true";
      type decimal64 {
        fraction-digits 2;
      }
    }
  }
  grouping SetPoEMaxPowerAvailableRequest {
    leaf MaxPowerAvailable {
      mandatory "true";
      type int32;
    }
  }
  rpc intri-poe-PoE-GetConfig {
    output {
      uses Config;
    }
  }
  rpc intri-poe-PoE-UpdatePortConfig {
    input {
      uses PortConfig;
    }
  }
  rpc intri-poe-PoE-RunRestartPoEPort {
    input {
      uses intri-device:PortList;
    }
  }
  rpc intri-poe-PoE-SetPoEMaxPowerAvailable {
    input {
      uses SystemBudget;
    }
  }
  rpc intri-poe-PoE-GetPortStatus {
    input {
      uses intri-device:PortList;
    }
    output {
      uses PortStatus;
    }
  }
  rpc intri-poe-PoE-GetSystemStatus {
    output {
      uses SystemStatus;
    }
  }
}
