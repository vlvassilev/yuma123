module intri-network {
  namespace "intri:intri-network";
  prefix "intri-network";
  import networkpb {
    prefix "networkpb";
  }
  import commonpb {
    prefix "commonpb";
  }
  organization "Intrising Inc.";
  contact "xxx@intrising.com.tw";
  revision 2022-06-14 {
    description "Build date.";
  }
}
