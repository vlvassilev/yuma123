module test-unversioned-module-imports-augment {

  namespace "http://yuma123.org/ns/test-unversioned-module-imports-augmentation";
  prefix tumia;

  import test-unversioned-module-imports-top { prefix tumit; }

  organization  "yuma123.org";
  
  description "Model for testing yangcli unversioned module imports resolution. Augment part.";
  
  revision 2018-03-28 {
    description
      "2.nd version. This newer version of the modules (with bar and bar2 leafs instead of foo and foo2) is available on the client side.";
  }

  revision 2018-03-27 {
    description
      "1.st version";
  }

  augment /tumit:top {
      leaf bar2 {
          type string;
      }
  }
}
