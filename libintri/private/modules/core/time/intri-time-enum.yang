submodule intri-time-enum {
  belongs-to "intri-time" {
    prefix "intri-time-enum";
  }
  revision 2022-06-14 {
    description "Build date.";
  }
  // core/time/time.proto
  typedef StatusTypeOptions {
    type enumeration {
      enum STATUS_TYPE_UNSET {
        description "[Unset]";
        value 0;
      }
      enum STATUS_TYPE_MANUALLY_SET {
        description "[Manually Set]";
        value 1;
      }
      enum STATUS_TYPE_SYNCHRONIZED {
        description "[Synchronized]";
        value 2;
      }
      enum STATUS_TYPE_SYNC_FAILED {
        description "[Sync Failed]";
        value 3;
      }
      enum STATUS_TYPE_DAY_LIGHT_SAVING_TIME {
        description "[Day Light Saving Time]";
        value 4;
      }
      enum STATUS_TYPE_GNSS_SET {
        description "[GNSS Set]";
        value 5;
      }
      enum STATUS_TYPE_GNSS_FAILED {
        description "[GNSS Failed]";
        value 6;
      }
      enum STATUS_TYPE_PTP_SET {
        description "[PTP Set]";
        value 7;
      }
      enum STATUS_TYPE_PTP_FAILED {
        description "[PTP Failed]";
        value 8;
      }
    }
  }
  // core/time/time.proto
  typedef ModeTypeOptions {
    type enumeration {
      enum MODE_TYPE_MANUAL {
        description "[Manual]";
        value 0;
      }
      enum MODE_TYPE_AUTO {
        description "[Auto (Use NTP)] Time mode auto requires Internet access and will get the time from the given main NTP server";
        value 1;
      }
      enum MODE_TYPE_GNSS {
        description "[GNSS]";
        value 2;
      }
      enum MODE_TYPE_PTP {
        description "[PTP]";
        value 3;
      }
    }
  }
}
