module intri-error {

  namespace "intri:intri-error";
  prefix "intri-error";
  organization "
    Intrising Inc.";
  contact "
    intrising@intrising.com.tw";
  revision 2022-06-24 {
    description "Build date.";
  }

  typedef ErrorTypeOptions {
    type enumeration {
      enum ERROR_TYPE_UNKNOWN {
        description "unexpected error";
        value 0;
      }
      enum ERROR_TYPE_OTHER_SERVICES {
        description "errpr from other services";
        value 1;
      }
      enum ERROR_TYPE_LIST_FULL {
        description "the %s must contain between %s and %s items, inclusive";
        value 2;
      }
      enum ERROR_TYPE_UNREACHABLE {
        description "the ip address %s is unreachable";
        value 3;
      }
      enum ERROR_TYPE_CONFIG_EMPTY {
        description "configuration is empty";
        value 10;
      }
      enum ERROR_TYPE_VLAN_TAGGED_LIST_SHOULD_BE_EMPTY {
        description "the interface %s tagged list should be empty when the mode is %s";
        value 11;
      }
      enum ERROR_TYPE_VLAN_UNTAGGED_LIST_SHOULD_BE_EMPTY {
        description "the interface %s untagged list should be empty when the mode is %s";
        value 12;
      }
      enum ERROR_TYPE_DIAGNOSTIC_DNS_EMPTY {
        description "the DNS name cannot be empty";
        value 13;
      }
      enum ERROR_TYPE_DIAGNOSTIC_DNS_NOT_FOUND {
        description "the server can't find %s";
        value 14;
      }
      enum ERROR_TYPE_BOARD_INFO_EMPTY {
        description "board info is empty";
        value 15;
      }
      enum ERROR_TYPE_FILE_EXTENSION_INVALID {
        description "the file extension %s is invalid";
        value 100;
      }
      enum ERROR_TYPE_FILE_URL_SCHEME_INVALID {
        description "the file url scheme %s is invalid";
        value 101;
      }
      enum ERROR_TYPE_CONFIG_FILE_SAME_AS_LOCAL_INVALID {
        description "the file %s is the same as the local configuration";
        value 102;
      }
      enum ERROR_TYPE_STP_PRIORITY_INVALID {
        description "the priorirty %s  should be a multiple of 4096";
        value 110;
      }
      enum ERROR_TYPE_INTERFACE_PORT_INVALID {
        description "the interface port %s does not allowed to be updated";
        value 111;
      }
      enum ERROR_TYPE_INTERFACE_VLAN_INVALID {
        description "the interface vlan %s does not allowed to be updated";
        value 112;
      }
      enum ERROR_TYPE_INTERFACE_TRUNK_INVALID {
        description "the interface trunk %s does not allowed to be updated";
        value 113;
      }
      enum ERROR_TYPE_VLAN_Q_IN_Q_ETHER_TYPE_INVALID {
        description "the interface %s Q-in-Q ether type does not allowed to set %s when the mode is %s";
        value 114;
      }
      enum ERROR_TYPE_MAINTENANCE_FIRMWARE_INVALID {
        description "the firmware file is invalid";
        value 120;
      }
      enum ERROR_TYPE_CRT_FILE_URL_SCHEME_INVALID {
        description "the crt file url scheme %s is invalid";
        value 121;
      }
      enum ERROR_TYPE_KEY_FILE_URL_SCHEME_INVALID {
        description "the key file url scheme %s is invalid";
        value 122;
      }
      enum ERROR_TYPE_CA_FILE_URL_SCHEME_INVALID {
        description "the ca file url scheme %s is invalid";
        value 123;
      }
      enum ERROR_TYPE_CRT_CONTENT_INVALID {
        description "the crt content is invalid";
        value 124;
      }
      enum ERROR_TYPE_CA_CONTENT_INVALID {
        description "the ca content is invalid";
        value 125;
      }
      enum ERROR_TYPE_TIME_ZONE_INVALID {
        description "the time zone %s is invalid";
        value 126;
      }
      enum ERROR_TYPE_TIME_DATE_TIME_INVALID {
        description "the time datetime %s is invalid";
        value 127;
      }
      enum ERROR_TYPE_POE_FIRMWARE_VERSION_INVALID {
        description "the verison is invalid";
        value 128;
      }
      enum ERROR_TYPE_DHCP_CUSTOM_REMOTE_ID_INVALID {
        description "the custom_remote ID can't be empty when the remote ID source is user defined";
        value 129;
      }
      enum ERROR_TYPE_DHCP_SERVER_BASIC_IP_INVALID {
        description "the basic ip range of the DHCP Server is invalid";
        value 130;
      }
      enum ERROR_TYPE_DHCP_SERVER_BASIC_LEASE_TIME_INVALID {
        description "the basic lease time of the DHCP Server is invalid";
        value 131;
      }
      enum ERROR_TYPE_DHCP_SERVER_MAC_BASED_IP_INVALID {
        description "the ip of the macBased entry is invalid";
        value 132;
      }
      enum ERROR_TYPE_DHCP_SERVER_MAC_BASED_MACADDRESS_INVALID {
        description "the macAddress of the macBased entry is invalid";
        value 133;
      }
      enum ERROR_TYPE_DHCP_SERVER_PORT_BASED_IP_INVALID {
        description "the ip of the portBased entry is invalid";
        value 134;
      }
      enum ERROR_TYPE_DHCP_SERVER_PORT_BASED_PORT_NO_INVALID {
        description "the portNo of the portBased entry is invalid";
        value 135;
      }
      enum ERROR_TYPE_FILE_WRITE_FAILED {
        description "the file %s write failed";
        value 201;
      }
      enum ERROR_TYPE_CONFIG_IMPORT_FAILED {
        description "import config failed";
        value 202;
      }
      enum ERROR_TYPE_CONFIG_EXPORT_FAILED {
        description "export config failed";
        value 203;
      }
      enum ERROR_TYPE_CONFIG_FILE_READ_FAILED {
        description "the file %s read failed";
        value 204;
      }
      enum ERROR_TYPE_CONFIG_FILE_UNMARSHAL_FALIED {
        description "the file %s unmarshals failed";
        value 205;
      }
      enum ERROR_TYPE_CONFIG_FILE_VALIDATE_FAILED {
        description "the file %s validates failed, because %s";
        value 206;
      }
      enum ERROR_TYPE_CONFIG_FILE_WRITE_FAILED {
        description "the file %s write failed";
        value 207;
      }
      enum ERROR_TYPE_CONFIG_MARSHAL_FALIED {
        description "the file %s marshal failed";
        value 208;
      }
      enum ERROR_TYPE_CLI_ACTION_FAILED {
        description "the file run script failed, because %s";
        value 210;
      }
      enum ERROR_TYPE_ACCESS_AUTHENTICATION_FAILED {
        description "authentication failed  , because %s";
        value 211;
      }
      enum ERROR_TYPE_DIAGNOSTIC_TRACE_ROUTE_FAILED {
        description "to execute trace route failed";
        value 212;
      }
      enum ERROR_TYPE_MAINTENANCE_EXECUTE_FAILED {
        description "execute the snapshot fail because %s";
        value 214;
      }
      enum ERROR_TYPE_MAINTENANCE_UPLOAD_FAILED {
        description "the file %s is uploading fail";
        value 215;
      }
      enum ERROR_TYPE_MAINTENANCE_DOWNLOAD_FAILED {
        description "the file %s is downloading fail";
        value 216;
      }
      enum ERROR_TYPE_MAINTENANCE_UPGRADE_FAILED {
        description "the file %s is upgrading fail";
        value 217;
      }
      enum ERROR_TYPE_CRT_DOWNLOAD_FAILED {
        description "the crt file %s is downloading fail";
        value 218;
      }
      enum ERROR_TYPE_KEY_DOWNLOAD_FAILED {
        description "the key file %s is downloading fail";
        value 219;
      }
      enum ERROR_TYPE_CA_DOWNLOAD_FAILED {
        description "the ca file %s is downloading fail";
        value 220;
      }
      enum ERROR_TYPE_CRT_UPLOAD_FAILED {
        description "the crt file %s is uploading fail";
        value 221;
      }
      enum ERROR_TYPE_KEY_UPLOAD_FAILED {
        description "the key file %s is uploading fail";
        value 222;
      }
      enum ERROR_TYPE_CA_UPLOAD_FAILED {
        description "the ca file %s is uploading fail";
        value 223;
      }
      enum ERROR_TYPE_TIME_PARSE_FAILED {
        description "the format %s is invalid";
        value 224;
      }
      enum ERROR_TYPE_I2C_READ_FAILED {
        description "I2C read failed";
        value 225;
      }
      enum ERROR_TYPE_I2C_WRITE_FAILED {
        description "I2C write failed";
        value 226;
      }
      enum ERROR_TYPE_POE_COMMAND_FAILED {
        description "PoE command failed";
        value 227;
      }
      enum ERROR_TYPE_ID_OUT_OF_RANGE {
        description "the id %s must be inside range [%s, %s]";
        value 300;
      }
      enum ERROR_TYPE_GROUP_ID_OUT_OF_RANGE {
        description "the group id %s must be inside range [%s, %s]";
        value 301;
      }
      enum ERROR_TYPE_ENTRY_OUT_OF_RANGE {
        description "The quantity of entries has reached the limit of maximum entries [%s]";
        value 302;
      }
      enum ERROR_TYPE_STP_HELLO_TIME_OUT_OF_RANGE {
        description "max age need to meet formulas: MaxAge >= (2x(HelloTime+1))";
        value 310;
      }
      enum ERROR_TYPE_STP_MAX_AGE_OUT_OF_RANGE {
        description "max age need to meet formulas: (2x(ForwardDelay-1)) >= MaxAge >= (2x(HelloTime+1))";
        value 311;
      }
      enum ERROR_TYPE_STP_FORWARD_DELAY_OUT_OF_RANGE {
        description "\tmax age need to meet formulas: (2x(ForwardDelay-1)) >= MaxAge";
        value 312;
      }
      enum ERROR_TYPE_QOS_QUEUE_NO_OUT_OF_RANGE {
        description "the queueNo %s must be inside range [%s, %s]";
        value 313;
      }
      enum ERROR_TYPE_QOS_PRIORITY_OUT_OF_RANGE {
        description "the priority %s must be inside range [%s, %s]";
        value 314;
      }
      enum ERROR_TYPE_QOS_COS_NO_OUT_OF_RANGE {
        description "the cosNo %s must be inside range [%s, %s]";
        value 315;
      }
      enum ERROR_TYPE_QOS_DSCP_NO_OUT_OF_RANGE {
        description "the dscpNo %s must be inside range [%s, %s]";
        value 316;
      }
      enum ERROR_TYPE_AU_DROP_LIST_OUT_OF_RANGE {
        description "the %s must contain between %s and %s items, inclusive";
        value 320;
      }
      enum ERROR_TYPE_AU_FORWARD_LIST_OUT_OF_RANGE {
        description "the %s must contain between %s and %s items, inclusive";
        value 321;
      }
      enum ERROR_TYPE_AU_LIMIT_OUT_OF_RANGE {
        description "the %s must contain between %s and %s items, inclusive";
        value 322;
      }
      enum ERROR_TYPE_AU_SECUTIRY_LEARNING_OUT_OF_RANGE {
        description "the %s must contain between %s and %s items, inclusive";
        value 323;
      }
      enum ERROR_TYPE_VLAN_GROUP_ID_OUT_OF_RANGE {
        description "the %s must contain between %s and %s items, inclusive";
        value 324;
      }
      enum ERROR_TYPE_LACP_GROUP_MEMBER_OUT_OF_RANGE {
        description "the %s must contain between %s and %s items, inclusive";
        value 325;
      }
      enum ERROR_TYPE_LACP_PRIORITY_OUT_OF_RANGE {
        description "the %s must contain between %s and %s items, inclusive";
        value 326;
      }
      enum ERROR_TYPE_LACP_ID_OUT_OF_RANGE {
        description "the %s must contain between %s and %s items, inclusive";
        value 327;
      }
      enum ERROR_TYPE_MIRRORING_SESSION_OUT_OF_RANGE {
        description "The quantity of sessions has reached the limit of maximum sessions [%s]";
        value 330;
      }
      enum ERROR_TYPE_HW_VALUE_OUT_OF_RANGE {
        description "the value %s must be inside range [%s, %s]";
        value 331;
      }
      enum ERROR_TYPE_POE_KEY_OUT_OF_RANGE {
        description "the value %s must be inside range [%s, %s]";
        value 332;
      }
      enum ERROR_TYPE_POE_BUDGET_OUT_OF_RANGE {
        description "the value %s must be inside range [%s, %s]";
        value 333;
      }
      enum ERROR_TYPE_MONITOR_SCORLL_VALUE_OUT_OF_RANGE {
        description "the value %s must be inside range [%s, %s]";
        value 334;
      }
      enum ERROR_TYPE_NAME_NOT_EXIST {
        description "the name %s does not exist";
        value 400;
      }
      enum ERROR_TYPE_ID_NOT_EXIST {
        description "the id %s does not exist";
        value 401;
      }
      enum ERROR_TYPE_INDEX_NOT_EXIST {
        description "the index %s does not exist";
        value 402;
      }
      enum ERROR_TYPE_GROUP_ID_NOT_EXIST {
        description "the group id %s does not exist";
        value 404;
      }
      enum ERROR_TYPE_MAC_ADDRESS_NOT_EXIST {
        description "the mac addres %s does not exist";
        value 405;
      }
      enum ERROR_TYPE_ENTRY_NOT_EXIST {
        description "the entry %s does not exist";
        value 406;
      }
      enum ERROR_TYPE_INTERFACE_NOT_EXIST {
        description "the interface does not exist";
        value 410;
      }
      enum ERROR_TYPE_INTERFACE_PORT_NOT_EXIST {
        description "the interface port %s does not exist";
        value 411;
      }
      enum ERROR_TYPE_INTERFACE_VLAN_NOT_EXIST {
        description "the interface vlan %s does not exist";
        value 412;
      }
      enum ERROR_TYPE_INTERFACE_TRUNK_NOT_EXIST {
        description "the interface trunk %s does not exist";
        value 413;
      }
      enum ERROR_TYPE_QOS_QUEUE_NO_NOT_EXIST {
        description "the queueNo %s does not exist in queue list";
        value 420;
      }
      enum ERROR_TYPE_ACCESS_SERVER_NAME_NOT_EXIST {
        description "the authentication server name %s does not exist";
        value 421;
      }
      enum ERROR_TYPE_ACCESS_GROUP_NAME_NOT_EXIST {
        description "the group name %s does not exist";
        value 422;
      }
      enum ERROR_TYPE_ACCESS_RESTRICTION_NAME_NOT_EXIST {
        description "the restriction name %s does not exist";
        value 423;
      }
      enum ERROR_TYPE_ACCESS_USER_NAME_NOT_EXIST {
        description "the user name %s does not exist";
        value 424;
      }
      enum ERROR_TYPE_ACL_BINDING_NAME_NOT_EXIST {
        description "the binding name %s does not exist";
        value 430;
      }
      enum ERROR_TYPE_ACL_FLOW_NAME_NOT_EXIST {
        description "the flow name %s does not exist";
        value 431;
      }
      enum ERROR_TYPE_ACL_RULE_NAME_NOT_EXIST {
        description "the rule name %s does not exist";
        value 432;
      }
      enum ERROR_TYPE_ACL_NAME_NOT_EXIST {
        description "the name %s does not exist";
        value 433;
      }
      enum ERROR_TYPE_ACL_INGRESS_RULE_NAME_NOT_EXIST {
        description "the ingress rule name %s does not exist";
        value 434;
      }
      enum ERROR_TYPE_ACL_EGRESS_RULE_NAME_NOT_EXIST {
        description "the egress rule name %s does not exist";
        value 435;
      }
      enum ERROR_TYPE_VLAN_FILTER_ID_NOT_EXIST {
        description "the filter id %s does not exist";
        value 440;
      }
      enum ERROR_TYPE_VLAN_GROUP_ID_NOT_EXIST {
        description "the group id %s does not exist";
        value 441;
      }
      enum ERROR_TYPE_VLAN_MANAGEMENT_VLAN_ID_NOT_EXIST {
        description "the management vlan id %s does not exist in filter list(the vlan filter should be enabled)";
        value 442;
      }
      enum ERROR_TYPE_VLAN_UNAUTHORIZED_VLAN_ID_NOT_EXIST {
        description "the unauthorized vlan id %s does not exist in filter list(the vlan filter should be enabled)";
        value 443;
      }
      enum ERROR_TYPE_VLAN_DEFAULT_VLAN_ID_NOT_EXIST {
        description "the interface %s default vlan id %s does not exist in filter list(the vlan filter should be enabled)";
        value 444;
      }
      enum ERROR_TYPE_VLAN_TAGGED_VLAN_ID_NOT_EXIST {
        description "the interface %s tagged vlan id %s does not exist in filter list(the vlan filter should be enabled)";
        value 445;
      }
      enum ERROR_TYPE_VLAN_UNTAGGED_VLAN_ID_NOT_EXIST {
        description "the interface %s untagged vlan id %s does not exist in filter list(the vlan filter should be enabled)";
        value 446;
      }
      enum ERROR_TYPE_VLAN_SOURCE_VLAN_ID_NOT_EXIST {
        description "the source vlan id %s does not exist in filter list";
        value 447;
      }
      enum ERROR_TYPE_VLAN_TRANSLATED_VLAN_ID_NOT_EXIST {
        description "the translated vlan id %s does not exist in filter list";
        value 448;
      }
      enum ERROR_TYPE_FILES_WEB_CERTIFICATE_ID_NOT_EXIST {
        description "the certificate id %s does not exist";
        value 450;
      }
      enum ERROR_TYPE_FILES_SNMP_CERTIFICATE_ID_NOT_EXIST {
        description "the certificate id %s does not exist";
        value 451;
      }
      enum ERROR_TYPE_FILES_SNMP_MANAGER_CERTIFICATE_ID_NOT_EXIST {
        description "the certificate id %s does not exist";
        value 452;
      }
      enum ERROR_TYPE_FILES_SNMP_MANAGER_USER_NOT_EXIST {
        description "the user %s does not exist";
        value 453;
      }
      enum ERROR_TYPE_AU_DROP_ENTRY_NOT_EXIST {
        description "the drop entry %s does not exist";
        value 460;
      }
      enum ERROR_TYPE_AU_FORWARD_ENTRY_NOT_EXIST {
        description "the forward entry %s does not exist";
        value 461;
      }
      enum ERROR_TYPE_AU_MULTICAST_ENTRY_NOT_EXIST {
        description "the multicast entry %s does not exist";
        value 462;
      }
      enum ERROR_TYPE_MULTICAST_IGMP_VLAN_ID_NOT_EXIST {
        description "the multicast igmp vlan id %s does not exist";
        value 465;
      }
      enum ERROR_TYPE_MULTICAST_MLD_VLAN_ID_NOT_EXIST {
        description "the multicast mld vlan id %s does not exist";
        value 466;
      }
      enum ERROR_TYPE_MULTICAST_UNREGISTERED_VLAN_ID_NOT_EXIST {
        description "the multicast unregistered vlan id %s does not exist";
        value 467;
      }
      enum ERROR_TYPE_POE_FIRMWARE_VERSION_NOT_EXIST {
        description "the verison does not exist";
        value 468;
      }
      enum ERROR_TYPE_NAME_EXIST {
        description "the name %s exists";
        value 500;
      }
      enum ERROR_TYPE_ID_EXIST {
        description "the id %s exists";
        value 501;
      }
      enum ERROR_TYPE_GROUP_ID_EXIST {
        description "the group id %s exists";
        value 502;
      }
      enum ERROR_TYPE_MAC_ADDRESS_EXIST {
        description "the mac addres %s exists";
        value 503;
      }
      enum ERROR_TYPE_INDEX_EXIST {
        description "the index %s exists";
        value 504;
      }
      enum ERROR_TYPE_ENTRY_EXIST {
        description "the entry exists";
        value 505;
      }
      enum ERROR_TYPE_INTERFACE_PORT_EXIST {
        description "the interface port %s exists";
        value 510;
      }
      enum ERROR_TYPE_INTERFACE_VLAN_EXIST {
        description "the interface vlan %s exists";
        value 511;
      }
      enum ERROR_TYPE_INTERFACE_TRUNK_EXIST {
        description "the interface trunk %s exists";
        value 512;
      }
      enum ERROR_TYPE_ACCESS_SERVER_NAME_EXIST {
        description "the authentication server name %s exists";
        value 520;
      }
      enum ERROR_TYPE_ACCESS_GROUP_NAME_EXIST {
        description "the group name %s exists";
        value 521;
      }
      enum ERROR_TYPE_ACCESS_RESTRICTION_NAME_EXIST {
        description "the restriction name %s exists";
        value 522;
      }
      enum ERROR_TYPE_ACCESS_USER_NAME_EXIST {
        description "the user name %s exists";
        value 523;
      }
      enum ERROR_TYPE_AU_DROP_ENTRY_EXIST {
        description "the entry %s exists";
        value 524;
      }
      enum ERROR_TYPE_AU_FORWARD_ENTRY_EXIST {
        description "the forwarad entry %s exists";
        value 525;
      }
      enum ERROR_TYPE_ACL_BINDING_NAME_EXIST {
        description "the binding name %s exits";
        value 526;
      }
      enum ERROR_TYPE_ACL_FLOW_NAME_EXIST {
        description "the flow name %s exits";
        value 527;
      }
      enum ERROR_TYPE_ACL_RULE_NAME_EXIST {
        description "the rule name %s exits";
        value 528;
      }
      enum ERROR_TYPE_ACL_NAME_EXIST {
        description "the name %s exists";
        value 529;
      }
      enum ERROR_TYPE_VLAN_FILTER_ID_EXIST {
        description "the filter id %s exists";
        value 530;
      }
      enum ERROR_TYPE_VLAN_GROUP_ID_EXIST {
        description "the group id %s exists";
        value 531;
      }
      enum ERROR_TYPE_VLAN_SOURCE_VLAN_ID_EXIST {
        description "the source vlan id %s exists in translated list";
        value 532;
      }
      enum ERROR_TYPE_FILES_SNMP_MANAGER_USER_EXIST {
        description "the user %s exists";
        value 533;
      }
      enum ERROR_TYPE_MULTICAST_STATIC_ENTRY_EXIST {
        description "the multicast entry %s exists";
        value 550;
      }
      enum ERROR_TYPE_ACL_RULE_PRIORITY_EXIST {
        description "the rule priorty %s exits";
        value 551;
      }
      enum ERROR_TYPE_FEATURE_NOT_SUPPORT {
        description "the feature is not supported";
        value 600;
      }
      enum ERROR_TYPE_URL_SCHEME_NOT_SUPPORT {
        description "the file url scheme %s does not support";
        value 601;
      }
      enum ERROR_TYPE_DEVICE_BOARD_NOT_SUPPORT {
        description "the board name %s is not supported";
        value 602;
      }
      enum ERROR_TYPE_INTERFACE_PORT_NOT_SUPPORT {
        description "the interface port %s is not supported";
        value 603;
      }
      enum ERROR_TYPE_INTERFACE_VLAN_NOT_SUPPORT {
        description "the interface vlan %s is not supported";
        value 604;
      }
      enum ERROR_TYPE_INTERFACE_TRUNK_NOT_SUPPORT {
        description "the interface trunk %s is not supported";
        value 605;
      }
      enum ERROR_TYPE_TIME_ZONE_NOT_SUPPORT {
        description "the time zone is not support";
        value 606;
      }
      enum ERROR_TYPE_NAME_OCCUPIED {
        description "the name %s is occupied.";
        value 650;
      }
      enum ERROR_TYPE_GROUP_ID_OCCUPIED {
        description "the group id %s is occupied";
        value 651;
      }
      enum ERROR_TYPE_VLAN_ID_OCCUPIED {
        description "the vlan id %s is occupied";
        value 652;
      }
      enum ERROR_TYPE_LACP_GROUP_MEMBER_OCCUPIED {
        description "the interface port %s is used by other trunk";
        value 653;
      }
      enum ERROR_TYPE_RSPAN_OCCUPIED {
        description "the RSPAN is occupied";
        value 654;
      }
      enum ERROR_TYPE_INTERFACE_OCCUPIED {
        description "the Interface %s is occupied";
        value 655;
      }
      enum ERROR_TYPE_VLAN_DEFAULT_VLAN_CAN_NOT_BE_CHANGED {
        description "the default vlan id %s can not be changed";
        value 900;
      }
      enum ERROR_TYPE_VLAN_TAGGED_LIST_INCLUDE_DEFAULT_VLAN {
        description "the interface %s tagged list should include default vlan id %s when the mode is %s";
        value 901;
      }
      enum ERROR_TYPE_VLAN_TAGGED_LIST_EXCLUDE_DEFAULT_VLAN {
        description "the interface %s tagged list should not include default vlan id %s when the mode is %s";
        value 902;
      }
      enum ERROR_TYPE_VLAN_UNTAGGED_LIST_INCLUDE_DEFAULT_VLAN {
        description "the interface %s untagged list should include default vlan id %s when the mode is %s";
        value 903;
      }
      enum ERROR_TYPE_VLAN_UNTAGGED_LIST_EXCLUDE_DEFAULT_VLAN {
        description "the interface %s untagged list should not include default vlan id %s when the mode is %s";
        value 904;
      }
      enum ERROR_TYPE_VLAN_GVRP_HOLD_TIMER_SHOULD_LESS_THAN_HALF_OF_JOIN_TIMER {
        description "the interface %s hold timer interval %s should less than half of join timer interval %s";
        value 905;
      }
      enum ERROR_TYPE_VLAN_GVRP_JOIN_TIMER_SHOULD_LESS_THAN_HALF_OF_LEAVE_TIMER {
        description "the interface %s join timer interval %s should less than half of leave timer interval %s";
        value 906;
      }
      enum ERROR_TYPE_VLAN_GVRP_LEAVE_TIMER_SHOULD_LESS_THAN_LEAVE_ALL_TIMER {
        description "the interface %s leave timer interval %s should less than leave all timer interval %s";
        value 907;
      }
      enum ERROR_TYPE_DHCP_CAN_NOT_ENABLE_SERVER {
        description "can't enable DHCPServer while DHCPRelay or DHCPClient is enabled";
        value 908;
      }
      enum ERROR_TYPE_DHCP_CAN_NOT_ENABLE_RELAY {
        description "can't enable DHCPRelay while DHCPServer or DHCPClient is enabled";
        value 909;
      }
      enum ERROR_TYPE_DHCP_SERVER_SERVER_DISABLED {
        description "can't do this action because dhcp server is disabled";
        value 910;
      }
      enum ERROR_TYPE_DHCP_SERVER_IP_RANGE_EQUAL {
        description "the start IP and end IP should not be equal";
        value 911;
      }
      enum ERROR_TYPE_DHCP_SERVER_START_IP_SHOULD_BE_SMALLER_THAN_END_IP {
        description "the start IP should be smaller than end IP";
        value 912;
      }
      enum ERROR_TYPE_MAINTENANCE_UPGRADING {
        description "the switch system is upgrading, please try again later";
        value 913;
      }
      enum ERROR_TYPE_NETWORK_MLD_ENABLED {
        description "IPv6 management cannot be disabled when MLD snooping is enabled";
        value 914;
      }
      enum ERROR_TYPE_NETWORK_ICMP_NOT_ENABLED {
        description "IPv6 ICMP auto address cannot be enabled when IPv6 management is disabled";
        value 915;
      }
      enum ERROR_TYPE_NETWORK_AUTO_NOT_ENABLED {
        description "IPv6 auto configuration cannot be enabled when IPv6 management is disabled";
        value 916;
      }
      enum ERROR_TYPE_NETWORK_STATIC_IP_NOT_CONFIGURED {
        description "IPv6 static IP address cannot be configuared when IPv6 management is disabled";
        value 917;
      }
      enum ERROR_TYPE_NETWORK_DNS_SERVER_NOT_CONFIGURED {
        description "IPv6 DNS server cannot be configuared when IPv6 management is disabled";
        value 918;
      }
      enum ERROR_TYPE_ACCESS_ENCRYPTED_PASSWORD_CREATED_FAILED {
        description "encrypted password creation error";
        value 919;
      }
      enum ERROR_TYPE_FILE_UNEXPECTED_ERROR {
        description "feil unexpected error";
        value 920;
      }
      enum ERROR_TYPE_NTP_NOT_ENABLE {
        description "NTP not enable";
        value 921;
      }
      enum ERROR_TYPE_COMMAND_EXECUTE_FAILED {
        description "OS command execute error";
        value 922;
      }
      enum ERROR_TYPE_MSTP_IS_UPDATEING {
        description "MSTP is updating, please wait";
        value 923;
      }
      enum ERROR_TYPE_MIRRORING_ERROR {
        description "Mirroring Err : %s";
        value 924;
      }
      enum ERROR_TYPE_PORT_SECURITY_ERROR {
        description "Port Security Err : %s";
        value 925;
      }
    }
  }
  grouping Detail {
    leaf Code {
      type uint64;
    }
  }
  grouping PreparingDetail {
    leaf ErrorOption {
      type ErrorTypeOptions;
    }
  }
}
