module yt11 {

   namespace "urn:ietf:params:xml:ns:yang:yt11";

   prefix "yt11";

   import yang-types { prefix yt; }

   organization "Netconf Central";

   contact "Andy Bierman";

   description "YANG test module 10. typdef chains";

   revision 2008-07-05 { description "initial version"; }

   leaf a1 { type int32; }

   container con1 {
      leaf a2 { type string; }
   }

   extension e1 {
     description "extension test";
     argument foo {
        yin-element true;
     }
   }

   leaf x { 
      type int32; 
   }

   grouping foo;

   extension bar;

   typedef my-str-type {
     description "Should fail because not a valid range restriction.";
     type my-base-str-type {
       length "1..42";
     }
     default "fred";
   }

   typedef my-base-str-type {
     type string {
       length "1..10";
     }
     status current;
     description "type description";
     reference "type external references";
   }

   
   leaf test-leaf {
     description "not an error if leaf uses type with errors";
     type my-str-type;
   }

   typedef pat1 {
     description "pattern test 1A";
     type string {
       pattern "[1-9]+";
     }
     default "111";
   }

   typedef pat2 {
     description "pattern test 1B; default should fail";
     type pat1 {
       pattern "[a-z]+";
     }
     default "fred";
   }

}
