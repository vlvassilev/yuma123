module intri-rmon {
  namespace "intri:intri-rmon";
  prefix "intri-rmon";
  import rmonpb {
    prefix "rmonpb";
  }
  organization "Intrising Inc.";
  contact "xxx@intrising.com.tw";
  revision 2022-06-14 {
    description "Build date.";
  }
}
