module intri-empty {

  namespace "intri:intri-empty";
  prefix "intri-empty";
  organization "
    Intrising Inc.";
  contact "
    intrising@intrising.com.tw";
  revision 2022-06-24 {
    description "Build date.";
  }

  grouping Empty {
  }
}
