module ieee-types {

    namespace "urn:ietf:params:xml:ns:yang:ieee-types:old";
    prefix "ieee";

    import yang-types { prefix yang; }

    organization
     "IETF NETMOD (NETCONF Data Modeling Language) Working Group";

    contact
     "WG Web:   <http://tools.ietf.org/wg/netmod/>
      WG List:  <mailto:netmod@ietf.org>

      WG Chair: David Partain
                <mailto:david.partain@ericsson.com>

      WG Chair: David Harrington
                <mailto:ietfdbh@comcast.net>

      Editor:   Juergen Schoenwaelder
                <mailto:j.schoenwaelder@jacobs-university.de>";

    description
     "This module contains a collection of generally useful derived
      YANG data types for IEEE 802 addresses and related things.

      Copyright (C) The IETF Trust (2008).  This version of this
      YANG module is part of RFC XXXX; see the RFC itself for full
      legal notices.";
    // RFC Ed.: replace XXXX with actual RFC number and remove this note

    revision 2008-11-03 {
      description
       "Initial revision, published as RFC XXXX";
    }
    // RFC Ed.: replace XXXX with actual RFC number and remove this note

    /*** collection of IEEE address type definitions ***/

    typedef mac-address {
      type string {
        pattern '[0-9a-fA-F]{2}(:[0-9a-fA-F]{2}){5}';
      }
      description
       "The mac-address type represents an 802 MAC address represented
        in the `canonical' order defined by IEEE 802.1a, i.e., as if it
        were transmitted least significant bit first, even though 802.5
        (in contrast to other 802.x protocols) requires MAC addresses
        to be transmitted most significant bit first.

        This type is in the value set and its semantics equivalent to
        the MacAddress textual convention of the SMIv2.";
      reference
        "RFC 2579: Textual Conventions for SMIv2";
    }

    /*** collection of IEEE 802 related identifier types ***/

    typedef bridgeid {
      type string {
        pattern '[0-9a-fA-F]{4}(:[0-9a-fA-F]{2}){6}';
      }
      description
       "The bridgeid type represents identifiers that uniquely
        identify a bridge.  Its first four hexadecimal digits
        contain a priority value followed by a colon. The
        remaining characters contain the MAC address used to
        refer to a bridge in a unique fashion (typically, the
        numerically smallest MAC address of all ports on the
        bridge).

        This type is in the value set and its semantics equivalent
        to the BridgeId textual convention of the SMIv2. However,
        since the BridgeId textual convention does not prescribe
        a lexical representation, the appearance might be different.";
      reference
       "RFC 4188: Definitions of Managed Objects for Bridges";
    }

    typedef vlanid {
      type uint16 {
        range "1..4094";
      }
      description
       "The vlanid type uniquely identifies a VLAN. This is the
        12-bit VLAN-ID used in the VLAN Tag header. The range is
        defined by the referenced specification.

        This type is in the value set and its semantics equivalent to
        the VlanId textual convention of the SMIv2.";
      reference
       "IEEE Std 802.1Q 2003 Edition: Virtual Bridged Local
                  Area Networks

        RFC 4363: Definitions of Managed Objects for Bridges with
                  Traffic Classes, Multicast Filtering, and Virtual
                  LAN Extensions";
    }

}
