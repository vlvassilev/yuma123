// Code generated by protoc-gen-yang. DO NOT EDIT.


/* ****************************************************************************************************
 * Import Path : "google.golang.org/genproto/googleapis/type/date"                                    *
 * Dir Path    : google.golang.org/genproto/googleapis/type/date                                      *
 * Go Package  : date                                                                                 *
 * Files       : 1                                                                                    *
 **************************************************************************************************** */
module intri-date {

  namespace "intri:intri-date";

  prefix "intri-date";

  organization "Intrising Inc.";

  contact "intrising@intrising.com.tw";

  revision 2022-06-23 {
    description "Build date.";
  }


  /* **************************************************************************************************
   * Msgs        : 1                                                                                  *
   ************************************************************************************************** */
  /* google/type/date.proto */
  grouping Date {
    leaf Year {
      type int32;
    }
    leaf Month {
      type int32;
    }
    leaf Day {
      type int32;
    }
  }

}
