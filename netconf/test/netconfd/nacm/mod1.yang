module mod1 {
  prefix m1;
  namespace "http://yuma123.org/ns/test/netconfd/nacm/mod1";

  container top {
    leaf foo {
      type string;
    }
    leaf bar {
      type string;
    }
    leaf baz {
      type string;
    }
  }
}
