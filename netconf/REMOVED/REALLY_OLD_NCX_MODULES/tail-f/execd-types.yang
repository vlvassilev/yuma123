submodule execd-types {

    belongs-to execd;

    description "Common types used within execd.";

    revision "2007-08-29" {
        description "Syntax fixes after pyang validation.";
    }
    revision "2007-06-08" {
        description "Initial revision.";
    }
    
    typedef prefixLengthIPv4 {
        type int32 {
            range "0..32";
        }
    }
    
    typedef prefixLengthIPv6 {
        type int32 {
            range "0..128";
        }
    }
    
    typedef interfaceName {
        type string {
            length "1..30";
            pattern "[A-Za-z][^/:.]*";
        }
    }
    
    typedef interfaceLogicalUnit {
        type int32 {
            range "0..9999";
        }
    }
}
