submodule execd-syslog {

    belongs-to execd;

    import yang-types { prefix yang; }
    import inet-types { prefix inet; }

    include execd-types;

    description
        "The 'syslog' component provides support for configuring logging to
         remote syslog servers.

         It is assumed to not be meaningful to allow for user
         configuration of syslog to local files/programs/users on a
         network device.";

    revision "2007-08-29" {
        description "Syntax fixes after pyang validation.";
    }
    revision "2007-06-08" {
        description "Initial revision.";
    }

    typedef syslogLevel {
        type enumeration {
            enum "emerg";
            enum "alert";
            enum "crit";
            enum "err";
            enum "warning";
            enum "notice";
            enum "info";
            enum "debug";
            enum "none";
            enum "all";
        }
    }
    
    typedef syslogFacility {
        type enumeration {
            enum "auth";
            enum "authpriv";
            enum "cron";
            enum "daemon";
            enum "ftp";
            enum "kern";
            enum "lpr";
            enum "mail";
            enum "news";
            enum "security";
            enum "syslog";
            enum "user";
            enum "uucp";
            enum "local0";
            enum "local1";
            enum "local2";
            enum "local3";
            enum "local4";
            enum "local5";
            enum "local6";
            enum "local7";
            enum "all";
        }
    }

    grouping syslog {
        list server {
            key name;
            leaf name {
                type inet:host;
            }
            leaf enabled {
                type boolean;
            }
            list selector {
                key name;
                leaf name {
                    type int32;
                }
                leaf negate {
                    type boolean;
                }
                leaf comparison {
                    type enumeration {
                        enum "same-or-higher";
                        enum "same";
                    }
                }
                leaf level {
                    type syslogLevel;
                }
                leaf-list facility {
                    type syslogFacility;
                    min-elements 1;
                    max-elements 8;
                }
            }
        }
    }
}
