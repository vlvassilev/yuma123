// Code generated by protoc-gen-yang. DO NOT EDIT.


/* ****************************************************************************************************
 * Import Path : "github.com/Intrising/intri-type/snmp"                                               *
 * Dir Path    : github.com/Intrising/intri-type/snmp                                                 *
 * Go Package  : snmp                                                                                 *
 * Files       : 2                                                                                    *
 **************************************************************************************************** */
module intri-snmp {

  namespace "intri:intri-snmp";

  prefix "intri-snmp";

  organization "Intrising Inc.";

  contact "intrising@intrising.com.tw";

  revision 2022-06-23 {
    description "Build date.";
  }

  import intri-userinterface {
    prefix intri-userinterface;
  }
  import intri-empty {
    prefix intri-empty;
  }
  import intri-access {
    prefix intri-access;
  }
  import intri-common {
    prefix intri-common;
  }
  import intri-files {
    prefix intri-files;
  }


  /* **************************************************************************************************
   * Msgs        : 1                                                                                  *
   ************************************************************************************************** */
  /* snmp/snmp.proto */
  grouping EngineInfo {
    leaf Boots {
      type int32;
    }
    leaf RunTime {
      type int64;
    }
  }


  /* **************************************************************************************************
   * Services    : 1                                                                                  *
   ************************************************************************************************** */

  /* **************************************************************************************************
   * Service     : SNMP                                                                               *
   * Methods     : 8                                                                                  *
   ************************************************************************************************** */
  /* snmp/service.proto */
  rpc intri-snmp-SetConfig {
    input  {
      uses intri-userinterface:SNMPConfig;
    }
  }
  /* snmp/service.proto */
  rpc intri-snmp-SetUsersConfig {
    input  {
      uses intri-access:UsersConfig;
    }
  }
  /* snmp/service.proto */
  rpc intri-snmp-SetGroupsConfig {
    input  {
      uses intri-access:GroupsConfig;
    }
  }
  /* snmp/service.proto */
  rpc intri-snmp-RunRestartSNMPServer {
    input  {
      uses intri-common:Confirm;
    }
  }
  /* snmp/service.proto */
  rpc intri-snmp-ActivateAgentCertificate {
    input  {
      uses intri-files:CertificateID;
    }
  }
  /* snmp/service.proto */
  rpc intri-snmp-ActivateManagerCertificate {
    input  {
      uses intri-files:CertificateUserIDList;
    }
  }
  /* snmp/service.proto */
  rpc intri-snmp-DeactivateManagerCertificate {
    input  {
      uses intri-files:CertificateUserID;
    }
  }
  /* snmp/service.proto */
  rpc intri-snmp-GetEngineInfo {
    output  {
      uses EngineInfo;
    }
  }

}
