module intri-poe {
  namespace "intri:intri-poe";
  prefix "intri-poe";
  import poepb {
    prefix "poepb";
  }
  organization "Intrising Inc.";
  contact "xxx@intrising.com.tw";
  revision 2022-06-14 {
    description "Build date.";
  }
}
