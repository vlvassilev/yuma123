// Code generated by protoc-gen-yang. DO NOT EDIT.


/* ****************************************************************************************************
 * Import Path : "github.com/Intrising/intri-type/timecontrol"                                        *
 * Dir Path    : github.com/Intrising/intri-type/timecontrol                                          *
 * Go Package  : timecontrol                                                                          *
 * Files       : 3                                                                                    *
 **************************************************************************************************** */
module intri-timecontrol {

  namespace "intri:intri-timecontrol";

  prefix "intri-timecontrol";

  organization "Intrising Inc.";

  contact "intrising@intrising.com.tw";

  revision 2022-06-23 {
    description "Build date.";
  }

  import intri-device {
    prefix intri-device;
  }
  import intri-timestamp {
    prefix intri-timestamp;
  }
  import intri-empty {
    prefix intri-empty;
  }


  /* **************************************************************************************************
   * Enums       : 6                                                                                  *
   ************************************************************************************************** */
  /* timecontrol/common.proto */
  typedef StatusInputBitTypeOptions {
    type enumeration {
      enum STATUS_INPUT_BIT_TYPE_LOS_LIVE {
        description "[Los Live] Status input bit type los live";
        value 0;
      }
      enum STATUS_INPUT_BIT_TYPE_NO_ACTIVITY_LIVE {
        description "[No Activity Live] Status input bit type no activity live";
        value 1;
      }
      enum STATUS_INPUT_BIT_TYPE_REQ_OFFS_LIM_LIVE {
        description "[Req Offs Lim Live] Status input bit type req offs lim live";
        value 2;
      }
      enum STATUS_INPUT_BIT_TYPE_TRANS_DETECT_LIVE {
        description "[Trans Detect Live] Status input bit type trans detect live";
        value 3;
      }
    }
  }
  /* timecontrol/common.proto */
  typedef DPLLManageIndexTypeOptions {
    type enumeration {
      enum DPLL_MANAGE_INDEX_0 {
        description "[Index 0] Manage index 0";
        value 0;
      }
      enum DPLL_MANAGE_INDEX_1 {
        description "[Index 1] Manage index 1";
        value 1;
      }
      enum DPLL_MANAGE_INDEX_2 {
        description "[Index 2] Manage index 2";
        value 2;
      }
      enum DPLL_MANAGE_INDEX_3 {
        description "[Index 3] Manage index 3";
        value 3;
      }
      enum DPLL_MANAGE_INDEX_4 {
        description "[Index 4] Manage index 4";
        value 4;
      }
      enum DPLL_MANAGE_INDEX_5 {
        description "[Index 5] Manage index 5";
        value 5;
      }
      enum DPLL_MANAGE_INDEX_6 {
        description "[Index 6] Manage index 6";
        value 6;
      }
      enum DPLL_MANAGE_INDEX_7 {
        description "[Index 7] Manage index 7";
        value 7;
      }
    }
  }
  /* timecontrol/common.proto */
  typedef DPLLStatusBitTypeOptions {
    type enumeration {
      enum DPLL_STATUS_BIT_TYPE_FREERUN {
        description "[Freerun] Freerun";
        value 0;
      }
      enum DPLL_STATUS_BIT_TYPE_LOCKACQ {
        description "[Lockacq] Lockacq";
        value 1;
      }
      enum DPLL_STATUS_BIT_TYPE_LOCKREC {
        description "[Lockrec] Lockrec";
        value 2;
      }
      enum DPLL_STATUS_BIT_TYPE_LOCKED {
        description "[Locked] Locked";
        value 3;
      }
      enum DPLL_STATUS_BIT_TYPE_HOLDOVER {
        description "[Holdover] Holdover";
        value 4;
      }
      enum DPLL_STATUS_BIT_TYPE_OPENLOOP {
        description "[Openloop] Openloop";
        value 5;
      }
      enum DPLL_STATUS_BIT_TYPE_DISABLED {
        description "[Disabled] Disabled";
        value 6;
      }
    }
  }
  /* timecontrol/common.proto */
  typedef DPLLRefPriorityBitTypeOptions {
    type enumeration {
      enum DPLL_REF_PRIORITY_BIT_TYPE_0 {
        description "[Priority 0] Dpll ref priority bit type 0";
        value 0;
      }
      enum DPLL_REF_PRIORITY_BIT_TYPE_1 {
        description "[Priority 1] Dpll ref priority bit type 1";
        value 1;
      }
      enum DPLL_REF_PRIORITY_BIT_TYPE_2 {
        description "[Priority 2] Dpll ref priority bit type 2";
        value 2;
      }
      enum DPLL_REF_PRIORITY_BIT_TYPE_3 {
        description "[Priority 3] Dpll ref priority bit type 3";
        value 3;
      }
      enum DPLL_REF_PRIORITY_BIT_TYPE_4 {
        description "[Priority 4] Dpll ref priority bit type 4";
        value 4;
      }
      enum DPLL_REF_PRIORITY_BIT_TYPE_5 {
        description "[Priority 5] Dpll ref priority bit type 5";
        value 5;
      }
      enum DPLL_REF_PRIORITY_BIT_TYPE_6 {
        description "[Priority 6] Dpll ref priority bit type 6";
        value 6;
      }
      enum DPLL_REF_PRIORITY_BIT_TYPE_7 {
        description "[Priority 7] Dpll ref priority bit type 7";
        value 7;
      }
      enum DPLL_REF_PRIORITY_BIT_TYPE_8 {
        description "[Priority 8] Dpll ref priority bit type 8";
        value 8;
      }
      enum DPLL_REF_PRIORITY_BIT_TYPE_9 {
        description "[Priority 9] Dpll ref priority bit type 9";
        value 9;
      }
      enum DPLL_REF_PRIORITY_BIT_TYPE_10 {
        description "[Priority 10] Dpll ref priority bit type 10";
        value 10;
      }
      enum DPLL_REF_PRIORITY_BIT_TYPE_11 {
        description "[Priority 11] Dpll ref priority bit type 11";
        value 11;
      }
      enum DPLL_REF_PRIORITY_BIT_TYPE_12 {
        description "[Priority 12] Dpll ref priority bit type 12";
        value 12;
      }
      enum DPLL_REF_PRIORITY_BIT_TYPE_13 {
        description "[Priority 13] Dpll ref priority bit type 13";
        value 13;
      }
      enum DPLL_REF_PRIORITY_BIT_TYPE_14 {
        description "[Priority 14] Dpll ref priority bit type 14";
        value 14;
      }
      enum DPLL_REF_PRIORITY_BIT_TYPE_15 {
        description "[Priority 15] Dpll ref priority bit type 15";
        value 15;
      }
      enum DPLL_REF_PRIORITY_BIT_TYPE_16 {
        description "[Priority 16] Dpll ref priority bit type 16";
        value 16;
      }
      enum DPLL_REF_PRIORITY_BIT_TYPE_17 {
        description "[Priority 17] Dpll ref priority bit type 17";
        value 17;
      }
      enum DPLL_REF_PRIORITY_BIT_TYPE_18 {
        description "[Priority 18] Dpll ref priority bit type 18";
        value 18;
      }
    }
  }
  /* timecontrol/common.proto */
  typedef ToDSourceTypeOptions {
    type enumeration {
      enum SYSTEM {
        description "[SYSTEM] Source system";
        value 0;
      }
      enum TIME_CONTROL {
        description "[TIME_CONTROL] Source time_control";
        value 1;
      }
      enum RTC {
        description "[RTC] Source rtc";
        value 2;
      }
      enum GPS {
        description "[GPS] Source gps";
        value 3;
      }
    }
  }
  /* timecontrol/common.proto */
  typedef DPLLToDTypeOptions {
    type enumeration {
      enum DPLL_MANAGE_TOD_0 {
        description "[ToD 0] ToD 0";
        value 0;
      }
      enum DPLL_MANAGE_TOD_1 {
        description "[ToD 1] ToD 1";
        value 1;
      }
      enum DPLL_MANAGE_TOD_2 {
        description "[ToD 2] ToD 2";
        value 2;
      }
      enum DPLL_MANAGE_TOD_3 {
        description "[ToD 3] ToD 3";
        value 3;
      }
    }
  }


  /* **************************************************************************************************
   * Msgs        : 29                                                                                 *
   ************************************************************************************************** */
  /* timecontrol/timecontrol.proto */
  grouping InputClockManage {
    container List {
      list List_Entry {
        uses InputClockManageEntry;
      }
    }
  }
  /* timecontrol/timecontrol.proto */
  grouping InputClockManageEntry {
    leaf InputCLK {
      type intri-device:InputClockTypeOptions;
    }
  }
  /* timecontrol/timecontrol.proto */
  grouping MonitorStatus {
    container List {
      list List_Entry {
        uses MonitorStatusEntry;
      }
    }
  }
  /* timecontrol/timecontrol.proto */
  grouping MonitorStatusEntry {
    leaf InputCLK {
      type intri-device:InputClockTypeOptions;
    }
    container StatusList {
      list StatusList_Entry {
        uses StatusInputBit;
      }
    }
    leaf Valid {
      type boolean;
    }
  }
  /* timecontrol/timecontrol.proto */
  grouping StatusInputBit {
    leaf Type {
      type StatusInputBitTypeOptions;
    }
    leaf Valid {
      type boolean;
    }
  }
  /* timecontrol/timecontrol.proto */
  grouping DPLLManage {
    container List {
      list List_Entry {
        uses DPLLManageEntry;
      }
    }
  }
  /* timecontrol/timecontrol.proto */
  grouping DPLLManageEntry {
    leaf Index {
      type DPLLManageIndexTypeOptions;
    }
  }
  /* timecontrol/timecontrol.proto */
  grouping DPLLStatus {
    container List {
      list List_Entry {
        uses DPLLStatusEntry;
      }
    }
  }
  /* timecontrol/timecontrol.proto */
  grouping DPLLStatusEntry {
    leaf Index {
      type DPLLManageIndexTypeOptions;
    }
    leaf StatusType {
      type DPLLStatusBitTypeOptions;
    }
    leaf InputCLK {
      type intri-device:InputClockTypeOptions;
    }
  }
  /* timecontrol/timecontrol.proto */
  grouping DPLLRefPriorityManage {
    container List {
      list List_Entry {
        uses DPLLRefPriorityManageEntry;
      }
    }
  }
  /* timecontrol/timecontrol.proto */
  grouping DPLLRefPriorityManageEntry {
    leaf Index {
      type DPLLManageIndexTypeOptions;
    }
    container PriorityList {
      leaf-list PriorityList_Entry {
        type DPLLRefPriorityBitTypeOptions;
      }
    }
  }
  /* timecontrol/timecontrol.proto */
  grouping DPLLRefPriority {
    container List {
      list List_Entry {
        uses DPLLRefPriorityEntry;
      }
    }
  }
  /* timecontrol/timecontrol.proto */
  grouping DPLLRefPriorityEntry {
    leaf Index {
      type DPLLManageIndexTypeOptions;
    }
    container PrioritList {
      list PrioritList_Entry {
        uses PriorityList;
      }
    }
  }
  /* timecontrol/timecontrol.proto */
  grouping PriorityList {
    leaf Priority {
      type DPLLRefPriorityBitTypeOptions;
    }
    leaf InputCLK {
      type intri-device:InputClockTypeOptions;
    }
  }
  /* timecontrol/timecontrol.proto */
  grouping SyncEInputClockSpeed {
    container List {
      list List_Entry {
        uses SyncEInputClockSpeedEntry;
      }
    }
  }
  /* timecontrol/timecontrol.proto */
  grouping SyncEInputClockSpeedEntry {
    leaf InputCLK {
      type intri-device:InputClockTypeOptions;
    }
    leaf Speed {
      type intri-device:PortPropertyTypeOptions;
    }
  }
  /* timecontrol/timecontrol.proto */
  grouping ToDSource {
    leaf Enable {
      type boolean;
    }
    leaf Source {
      type ToDSourceTypeOptions;
    }
  }
  /* timecontrol/timecontrol.proto */
  grouping DPLLToDManage {
    container List {
      list List_Entry {
        uses DPLLToDManageEntry;
      }
    }
  }
  /* timecontrol/timecontrol.proto */
  grouping DPLLToDManageEntry {
    leaf Index {
      type DPLLToDTypeOptions;
    }
  }
  /* timecontrol/timecontrol.proto */
  grouping ToDTime {
    container List {
      list List_Entry {
        uses ToDTimeEntry;
      }
    }
  }
  /* timecontrol/timecontrol.proto */
  grouping ToDTimeEntry {
    leaf Index {
      type DPLLToDTypeOptions;
    }
    container DateTime {
      uses intri-timestamp:Timestamp;
    }
  }
  /* timecontrol/timecontrol.proto */
  grouping DPLLFrequencyControl {
    container List {
      list List_Entry {
        uses DPLLFrequencyControlEntry;
      }
    }
  }
  /* timecontrol/timecontrol.proto */
  grouping DPLLFrequencyControlEntry {
    leaf Index {
      type DPLLManageIndexTypeOptions;
    }
    leaf FreqOffset {
      type int64;
    }
  }
  /* timecontrol/timecontrol.proto */
  grouping DPLLPhaseControl {
    container List {
      list List_Entry {
        uses DPLLPhaseControlEntry;
      }
    }
  }
  /* timecontrol/timecontrol.proto */
  grouping DPLLPhaseControlEntry {
    leaf Index {
      type DPLLManageIndexTypeOptions;
    }
    leaf PhOffset {
      type int32;
    }
  }
  /* timecontrol/timecontrol.proto */
  grouping DPLLPhaseSlopeLimit {
    container List {
      list List_Entry {
        uses DPLLPhaseSlopeLimitEntry;
      }
    }
  }
  /* timecontrol/timecontrol.proto */
  grouping DPLLPhaseSlopeLimitEntry {
    leaf Index {
      type DPLLManageIndexTypeOptions;
    }
    leaf Limit {
      type int32;
    }
  }
  /* timecontrol/timecontrol.proto */
  grouping DPLLPhaseControlTimer {
    container List {
      list List_Entry {
        uses DPLLPhaseControlTimerEntry;
      }
    }
  }
  /* timecontrol/timecontrol.proto */
  grouping DPLLPhaseControlTimerEntry {
    leaf Index {
      type DPLLManageIndexTypeOptions;
    }
    leaf Timeout {
      type int32;
    }
  }


  /* **************************************************************************************************
   * Services    : 1                                                                                  *
   ************************************************************************************************** */

  /* **************************************************************************************************
   * Service     : TimeControl                                                                        *
   * Methods     : 18                                                                                 *
   ************************************************************************************************** */
  /* timecontrol/service.proto */
  rpc intri-timecontrol-GetInputMonitorStatus {
    input  {
      uses InputClockManage;
    }
    output  {
      uses MonitorStatus;
    }
  }
  /* timecontrol/service.proto */
  rpc intri-timecontrol-GetDPLLStatus {
    input  {
      uses DPLLManage;
    }
    output  {
      uses DPLLStatus;
    }
  }
  /* timecontrol/service.proto */
  rpc intri-timecontrol-SetDPLLRefPriority {
    input  {
      uses DPLLRefPriority;
    }
  }
  /* timecontrol/service.proto */
  rpc intri-timecontrol-GetDPLLRefPriority {
    input  {
      uses DPLLRefPriorityManage;
    }
    output  {
      uses DPLLRefPriority;
    }
  }
  /* timecontrol/service.proto */
  rpc intri-timecontrol-SetInputClockFreq {
    input  {
      uses SyncEInputClockSpeed;
    }
  }
  /* timecontrol/service.proto */
  rpc intri-timecontrol-GetInputClockFreq {
    input  {
      uses InputClockManage;
    }
    output  {
      uses SyncEInputClockSpeed;
    }
  }
  /* timecontrol/service.proto */
  rpc intri-timecontrol-SetToDSource {
    input  {
      uses ToDSource;
    }
  }
  /* timecontrol/service.proto */
  rpc intri-timecontrol-GetToDSource {
    output  {
      uses ToDSource;
    }
  }
  /* timecontrol/service.proto */
  rpc intri-timecontrol-SetToD {
    input  {
      uses ToDTime;
    }
  }
  /* timecontrol/service.proto */
  rpc intri-timecontrol-GetToD {
    input  {
      uses DPLLToDManage;
    }
    output  {
      uses ToDTime;
    }
  }
  /* timecontrol/service.proto */
  rpc intri-timecontrol-SetFrequencyControl {
    input  {
      uses DPLLFrequencyControl;
    }
  }
  /* timecontrol/service.proto */
  rpc intri-timecontrol-GetFrequencyControl {
    input  {
      uses DPLLManage;
    }
    output  {
      uses DPLLFrequencyControl;
    }
  }
  /* timecontrol/service.proto */
  rpc intri-timecontrol-SetPhaseControl {
    input  {
      uses DPLLPhaseControl;
    }
  }
  /* timecontrol/service.proto */
  rpc intri-timecontrol-GetPhaseControl {
    input  {
      uses DPLLManage;
    }
    output  {
      uses DPLLPhaseControl;
    }
  }
  /* timecontrol/service.proto */
  rpc intri-timecontrol-SetPhaseSlopeLimit {
    input  {
      uses DPLLPhaseSlopeLimit;
    }
  }
  /* timecontrol/service.proto */
  rpc intri-timecontrol-GetPhaseSlopeLimit {
    input  {
      uses DPLLManage;
    }
    output  {
      uses DPLLPhaseSlopeLimit;
    }
  }
  /* timecontrol/service.proto */
  rpc intri-timecontrol-SetPhaseControlTimer {
    input  {
      uses DPLLPhaseControlTimer;
    }
  }
  /* timecontrol/service.proto */
  rpc intri-timecontrol-GetPhaseControlTimer {
    input  {
      uses DPLLManage;
    }
    output  {
      uses DPLLPhaseControlTimer;
    }
  }

}
