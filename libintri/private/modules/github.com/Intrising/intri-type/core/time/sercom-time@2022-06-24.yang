module sercom-time {

  namespace "sercom:sercom-time";
  prefix "sercom-time";
  organization "
    Sercomm Inc.";
  contact "
    sercomm@sercomm.com.tw";
  revision 2022-06-24 {
    description "Build date.";
  }

  import sercom-timestamp {
    prefix sercom-timestamp;
  }
  import sercom-empty {
    prefix sercom-empty;
  }
  import sercom-common {
    prefix sercom-common;
  }
  typedef StatusTypeOptions {
    type enumeration {
      enum STATUS_TYPE_UNSET {
        description "[Unset]";
        value 0;
      }
      enum STATUS_TYPE_MANUALLY_SET {
        description "[Manually Set]";
        value 1;
      }
      enum STATUS_TYPE_SYNCHRONIZED {
        description "[Synchronized]";
        value 2;
      }
      enum STATUS_TYPE_SYNC_FAILED {
        description "[Sync Failed]";
        value 3;
      }
      enum STATUS_TYPE_DAY_LIGHT_SAVING_TIME {
        description "[Day Light Saving Time]";
        value 4;
      }
      enum STATUS_TYPE_GNSS_SET {
        description "[GNSS Set]";
        value 5;
      }
      enum STATUS_TYPE_GNSS_FAILED {
        description "[GNSS Failed]";
        value 6;
      }
      enum STATUS_TYPE_PTP_SET {
        description "[PTP Set]";
        value 7;
      }
      enum STATUS_TYPE_PTP_FAILED {
        description "[PTP Failed]";
        value 8;
      }
    }
  }
  typedef ModeTypeOptions {
    type enumeration {
      enum MODE_TYPE_MANUAL {
        description "[Manual]";
        value 0;
      }
      enum MODE_TYPE_AUTO {
        description "[Auto (Use NTP)] Time mode auto requires Internet access and will get the time from the given main NTP server";
        value 1;
      }
      enum MODE_TYPE_GNSS {
        description "[GNSS]";
        value 2;
      }
      enum MODE_TYPE_PTP {
        description "[PTP]";
        value 3;
      }
    }
  }
  grouping Config {
    leaf Mode {
      mandatory "true";
      type ModeTypeOptions;
    }
    leaf MainNTPServer {
      mandatory "true";
      type string;
    }
    leaf BackupNTPServer {
      mandatory "true";
      type string;
    }
    leaf TrustedServerEnabled {
      mandatory "true";
      type boolean;
    }
    leaf SyncInterval {
      mandatory "true";
      type int32;
    }
    leaf TimeZone {
      mandatory "true";
      type string;
    }
    leaf TimeFormat {
      mandatory "true";
      type string;
    }
    leaf DateFormat {
      mandatory "true";
      type string;
    }
    leaf Manual {
      mandatory "true";
      type string;
    }
  }
  grouping ListTimeZones {
    container List {
      leaf-list List_Entry {
        type string;
      }
    }
  }
  grouping Status {
    leaf Status {
      mandatory "true";
      type StatusTypeOptions;
    }
    leaf LocalTime {
      mandatory "true";
      type string;
    }
    leaf LocalDate {
      mandatory "true";
      type string;
    }
    leaf UsedNTPServer {
      mandatory "true";
      type string;
    }
  }
  grouping RequestWithTimestamp {
    container Ts {
      uses sercom-timestamp:Timestamp;
    }
  }
  grouping RequestWithInt64 {
    leaf Ts {
      mandatory "true";
      type int64;
    }
  }
  grouping Response {
    leaf Ts {
      mandatory "true";
      type string;
    }
  }
  rpc sercom-time-Time-GetConfig {
    output {
      uses Config;
    }
  }
  rpc sercom-time-Time-SetConfig {
    input {
      uses Config;
    }
  }
  rpc sercom-time-Time-GetStatus {
    output {
      uses Status;
    }
  }
  rpc sercom-time-Time-GetTimeDate {
    output {
      uses sercom-common:DateTime;
    }
  }
  rpc sercom-time-Time-RunSyncNow {
  }
  rpc sercom-time-Time-RunListTimeZones {
    output {
      uses ListTimeZones;
    }
  }
}
