module test-re-match {
  yang-version 1.1;

  namespace "http://yuma123.org/ns/test-re-match";
  prefix trm;

  import ietf-interfaces {
    prefix if;
  }

  organization
    "example.com";

  description
    "Part of the re-match test.";

  revision 2017-07-13 {
    description
      "Initial version";
  }
  leaf test-re-match-string {
    type string;
    must 're-match(.,"\d{1,3}\.\d{1,3}\.\d{1,3}")';
  }

  augment "/if:interfaces/if:interface" {
    leaf count-eth0 {
      type uint32;
      must '/if:interfaces/if:interface[re-match(if:name, "eth0\.\d+")]';
    }
  }
}
