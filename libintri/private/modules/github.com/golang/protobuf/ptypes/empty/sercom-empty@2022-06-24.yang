module sercom-empty {

  namespace "sercom:sercom-empty";
  prefix "sercom-empty";
  organization "
    Sercomm Inc.";
  contact "
    sercomm@sercomm.com.tw";
  revision 2022-06-24 {
    description "Build date.";
  }

  grouping Empty {
  }
}
