// Code generated by protoc-gen-yang. DO NOT EDIT.


/* ****************************************************************************************************
 * Import Path : "github.com/Intrising/intri-type/core/maintenance"                                   *
 * Dir Path    : github.com/Intrising/intri-type/core/maintenance                                     *
 * Go Package  : maintenance                                                                          *
 * Files       : 2                                                                                    *
 **************************************************************************************************** */
module intri-maintenance {

  namespace "intri:intri-maintenance";

  prefix "intri-maintenance";

  organization "Intrising Inc.";

  contact "intrising@intrising.com.tw";

  revision 2022-06-23 {
    description "Build date.";
  }

  import intri-common {
    prefix intri-common;
  }
  import intri-empty {
    prefix intri-empty;
  }


  /* **************************************************************************************************
   * Msgs        : 2                                                                                  *
   ************************************************************************************************** */
  /* core/maintenance/maintenance.proto */
  grouping FirmwareInfo {
    leaf Version {
      type string;
    }
    leaf BuildDate {
      type string;
    }
    leaf BuildNumber {
      type string;
    }
  }
  /* core/maintenance/maintenance.proto */
  grouping UpgradePathRequest {
    leaf Path {
      type string;
    }
    leaf FTPSEnabled {
      type boolean;
    }
    leaf RebootAfterAction {
      type boolean;
    }
  }


  /* **************************************************************************************************
   * Services    : 1                                                                                  *
   ************************************************************************************************** */

  /* **************************************************************************************************
   * Service     : Maintenance                                                                        *
   * Methods     : 6                                                                                  *
   ************************************************************************************************** */
  /* core/maintenance/service.proto */
  rpc intri-maintenance-RunRebootDevice {
    input  {
      uses intri-common:Confirm;
    }
  }
  /* core/maintenance/service.proto */
  rpc intri-maintenance-RunCreateSnapshot {
    input  {
      uses intri-common:ExportPathRequest;
    }
  }
  /* core/maintenance/service.proto */
  rpc intri-maintenance-GetCurrentFirmware {
    output  {
      uses FirmwareInfo;
    }
  }
  /* core/maintenance/service.proto */
  rpc intri-maintenance-GetPreviousFirmware {
    output  {
      uses FirmwareInfo;
    }
  }
  /* core/maintenance/service.proto */
  rpc intri-maintenance-RunGotoPreviousFirmware {
    input  {
      uses intri-common:Confirm;
    }
  }
  /* core/maintenance/service.proto */
  rpc intri-maintenance-RunUpgradeFirmware {
    input  {
      uses UpgradePathRequest;
    }
  }

}
