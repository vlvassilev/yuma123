module intri-qos {
  namespace "intri:intri-qos";
  prefix "intri-qos";
  import qospb {
    prefix "qospb";
  }
  organization "Intrising Inc.";
  contact "xxx@intrising.com.tw";
  revision 2022-06-14 {
    description "Build date.";
  }
}
