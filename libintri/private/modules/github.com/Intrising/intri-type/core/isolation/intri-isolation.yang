// Code generated by protoc-gen-yang. DO NOT EDIT.


/* ****************************************************************************************************
 * Import Path : "github.com/Intrising/intri-type/core/isolation"                                     *
 * Dir Path    : github.com/Intrising/intri-type/core/isolation                                       *
 * Go Package  : isolation                                                                            *
 * Files       : 2                                                                                    *
 **************************************************************************************************** */
module intri-isolation {

  namespace "intri:intri-isolation";

  prefix "intri-isolation";

  organization "Intrising Inc.";

  contact "intrising@intrising.com.tw";

  revision 2022-06-23 {
    description "Build date.";
  }

  import intri-device {
    prefix intri-device;
  }
  import intri-empty {
    prefix intri-empty;
  }


  /* **************************************************************************************************
   * Msgs        : 2                                                                                  *
   ************************************************************************************************** */
  /* core/isolation/isolation.proto */
  grouping ConfigEntry {
    container IdentifyNo {
      uses intri-device:InterfaceIdentify;
    }
    container AllowOutgoingList {
      list AllowOutgoingList_Entry {
        uses intri-device:InterfaceIdentify;
      }
    }
  }
  /* core/isolation/isolation.proto */
  grouping Config {
    container List {
      list List_Entry {
        uses ConfigEntry;
      }
    }
  }


  /* **************************************************************************************************
   * Services    : 1                                                                                  *
   ************************************************************************************************** */

  /* **************************************************************************************************
   * Service     : Isolation                                                                          *
   * Methods     : 2                                                                                  *
   ************************************************************************************************** */
  /* core/isolation/service.proto */
  rpc intri-isolation-GetConfig {
    output  {
      uses Config;
    }
  }
  /* core/isolation/service.proto */
  rpc intri-isolation-SetAllowOutgoingConfig {
    input  {
      uses ConfigEntry;
    }
  }

}
