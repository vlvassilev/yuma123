// Code generated by protoc-gen-yang. DO NOT EDIT.


/* ****************************************************************************************************
 * Import Path : "github.com/Intrising/intri-type/core/time"                                          *
 * Dir Path    : github.com/Intrising/intri-type/core/time                                            *
 * Go Package  : time                                                                                 *
 * Files       : 2                                                                                    *
 **************************************************************************************************** */
module intri-time {

  namespace "intri:intri-time";

  prefix "intri-time";

  organization "Intrising Inc.";

  contact "intrising@intrising.com.tw";

  revision 2022-06-23 {
    description "Build date.";
  }

  import intri-timestamp {
    prefix intri-timestamp;
  }
  import intri-empty {
    prefix intri-empty;
  }
  import intri-common {
    prefix intri-common;
  }


  /* **************************************************************************************************
   * Enums       : 2                                                                                  *
   ************************************************************************************************** */
  /* core/time/time.proto */
  typedef StatusTypeOptions {
    type enumeration {
      enum STATUS_TYPE_UNSET {
        description "[Unset]";
        value 0;
      }
      enum STATUS_TYPE_MANUALLY_SET {
        description "[Manually Set]";
        value 1;
      }
      enum STATUS_TYPE_SYNCHRONIZED {
        description "[Synchronized]";
        value 2;
      }
      enum STATUS_TYPE_SYNC_FAILED {
        description "[Sync Failed]";
        value 3;
      }
      enum STATUS_TYPE_DAY_LIGHT_SAVING_TIME {
        description "[Day Light Saving Time]";
        value 4;
      }
      enum STATUS_TYPE_GNSS_SET {
        description "[GNSS Set]";
        value 5;
      }
      enum STATUS_TYPE_GNSS_FAILED {
        description "[GNSS Failed]";
        value 6;
      }
      enum STATUS_TYPE_PTP_SET {
        description "[PTP Set]";
        value 7;
      }
      enum STATUS_TYPE_PTP_FAILED {
        description "[PTP Failed]";
        value 8;
      }
    }
  }
  /* core/time/time.proto */
  typedef ModeTypeOptions {
    type enumeration {
      enum MODE_TYPE_MANUAL {
        description "[Manual]";
        value 0;
      }
      enum MODE_TYPE_AUTO {
        description "[Auto (Use NTP)] Time mode auto requires Internet access and will get the time from the given main NTP server";
        value 1;
      }
      enum MODE_TYPE_GNSS {
        description "[GNSS]";
        value 2;
      }
      enum MODE_TYPE_PTP {
        description "[PTP]";
        value 3;
      }
    }
  }


  /* **************************************************************************************************
   * Msgs        : 6                                                                                  *
   ************************************************************************************************** */
  /* core/time/time.proto */
  grouping Config {
    leaf Mode {
      type ModeTypeOptions;
    }
    leaf MainNTPServer {
      type string;
    }
    leaf BackupNTPServer {
      type string;
    }
    leaf TrustedServerEnabled {
      type boolean;
    }
    leaf SyncInterval {
      type int32;
    }
    leaf TimeZone {
      type string;
    }
    leaf TimeFormat {
      type string;
    }
    leaf DateFormat {
      type string;
    }
    leaf Manual {
      type string;
    }
  }
  /* core/time/time.proto */
  grouping ListTimeZones {
    container List {
      leaf-list List_Entry {
        type string;
      }
    }
  }
  /* core/time/time.proto */
  grouping Status {
    leaf Status {
      type StatusTypeOptions;
    }
    leaf LocalTime {
      type string;
    }
    leaf LocalDate {
      type string;
    }
    leaf UsedNTPServer {
      type string;
    }
  }
  /* core/time/time.proto */
  grouping RequestWithTimestamp {
    container Ts {
      uses intri-timestamp:Timestamp;
    }
  }
  /* core/time/time.proto */
  grouping RequestWithInt64 {
    leaf Ts {
      type int64;
    }
  }
  /* core/time/time.proto */
  grouping Response {
    leaf Ts {
      type string;
    }
  }


  /* **************************************************************************************************
   * Services    : 1                                                                                  *
   ************************************************************************************************** */

  /* **************************************************************************************************
   * Service     : Time                                                                               *
   * Methods     : 9                                                                                  *
   ************************************************************************************************** */
  /* core/time/service.proto */
  rpc intri-time-GetConfig {
    output  {
      uses Config;
    }
  }
  /* core/time/service.proto */
  rpc intri-time-SetConfig {
    input  {
      uses Config;
    }
  }
  /* core/time/service.proto */
  rpc intri-time-GetStatus {
    output  {
      uses Status;
    }
  }
  /* core/time/service.proto */
  rpc intri-time-GetTimeDate {
    output  {
      uses intri-common:DateTime;
    }
  }
  /* core/time/service.proto */
  rpc intri-time-RunSyncNow {
  }
  /* core/time/service.proto */
  rpc intri-time-RunListTimeZones {
    output  {
      uses ListTimeZones;
    }
  }
  /* core/time/service.proto */
  rpc intri-time-GetCorrectionTime {
    input  {
      uses RequestWithTimestamp;
    }
    output  {
      uses Response;
    }
  }
  /* core/time/service.proto */
  rpc intri-time-GetCorrectionTimeWithInt64 {
    input  {
      uses RequestWithInt64;
    }
    output  {
      uses Response;
    }
  }
  /* core/time/service.proto */
  rpc intri-time-GetUTC {
    output  {
      uses Response;
    }
  }

}
