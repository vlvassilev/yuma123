module intri-loop {
  namespace "intri:intri-loop";
  prefix "intri-loop";
  import looppb {
    prefix "looppb";
  }
  organization "Intrising Inc.";
  contact "xxx@intrising.com.tw";
  revision 2022-06-14 {
    description "Build date.";
  }
}
