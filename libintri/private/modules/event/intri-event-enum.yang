submodule intri-event-enum {
  belongs-to "intri-event" {
    prefix "intri-event-enum";
  }
  revision 2022-06-14 {
    description "Build date.";
  }
  // event/acl.proto
  typedef ACLActionTypeOptions {
    type enumeration {
      enum ACL_ACTION_TYPE_ADD {
        description "[Add] Add";
        value 0;
      }
      enum ACL_ACTION_TYPE_DELETE {
        description "[Delete] Delete";
        value 1;
      }
    }
  }
  // event/aggregation.proto
  typedef AggrTypeOptions {
    type enumeration {
      enum AGGR_TYPE_CLEAR {
        description "[Clear]";
        value 0;
      }
      enum AGGR_TYPE_UPDATE {
        description "[Update]";
        value 1;
      }
    }
  }
  // event/aggregation.proto
  typedef AggrSourceTypeOptions {
    type enumeration {
      enum AGGR_SOURCE_TYPE_TRUNK {
        description "[Trunk]";
        value 0;
      }
      enum AGGR_SOURCE_TYPE_LGPORT {
        description "[Lgport]";
        value 1;
      }
    }
  }
  // event/au.proto
  typedef AUParameterTypeOptions {
    type enumeration {
      enum AU_PARAMETER_TYPE_NORMAL {
        description "[Normal] Normal";
        value 0;
      }
      enum AU_PARAMETER_TYPE_PORT_SECURITY {
        description "[Port Security] Port Security";
        value 2;
      }
      enum AU_PARAMETER_TYPE_PACC {
        description "[Pacc] Pacc";
        value 3;
      }
    }
  }
  // event/au.proto
  typedef FDBEntryActionTypeOptions {
    type enumeration {
      enum FDB_ENTRY_ACTION_TYPE_ADD {
        description "[Add] Add";
        value 0;
      }
      enum FDB_ENTRY_ACTION_TYPE_DELETE {
        description "[Delete] Delete";
        value 1;
      }
      enum FDB_ENTRY_ACTION_TYPE_MOVE {
        description "[Move] Move";
        value 2;
      }
    }
  }
  // event/au.proto
  typedef MulticastEntryTypeOptions {
    type enumeration {
      enum MULTICAST_ENTRY_TYPE_MAC {
        description "[Mac] Mac";
        value 0;
      }
      enum MULTICAST_ENTRY_TYPE_IPV4 {
        description "[Ipv4] Ipv4";
        value 1;
      }
      enum MULTICAST_ENTRY_TYPE_IPV6 {
        description "[Ipv6] Ipv6";
        value 2;
      }
    }
  }
  // event/button.proto
  typedef ButtonTypeOptions {
    type enumeration {
      enum BUTTON_TYPE_RESET {
        description "[Reset]";
        value 0;
      }
    }
  }
  // event/button.proto
  typedef ButtonActionTypeOptions {
    type enumeration {
      enum BUTTON_ACTION_TYPE_PRESSED {
        description "[Pressed]";
        value 0;
      }
      enum BUTTON_ACTION_TYPE_RELEASED {
        description "[Released]";
        value 1;
      }
    }
  }
  // event/button.proto
  typedef ButtonTriggerActionTypeOptions {
    type enumeration {
      enum BUTTON_TRIGGER_ACTION_TYPE_REBOOT {
        description "[Reboot]";
        value 0;
      }
      enum BUTTON_TRIGGER_ACTION_TYPE_FACTORY {
        description "[Factory]";
        value 1;
      }
    }
  }
  // event/common.proto
  typedef LoggingTypeOptions {
    type enumeration {
      enum LOGGING_TYPE_NONE {
        description "[None] logging type \"None\"";
        value 0;
      }
      enum LOGGING_TYPE_ALIVE_TEST_EVENT {
        description "[Alive Test Event] logging type \"Alive Test Event\"";
        value 1;
      }
      enum LOGGING_TYPE_SELF_TEST {
        description "[Self Test] logging type \"Self Test\"";
        value 2;
      }
      enum LOGGING_TYPE_FIRMWARE_UPDATE_OK {
        description "[Firmware Update Ok] logging type \"Firmware Update Ok\"";
        value 10;
      }
      enum LOGGING_TYPE_FIRMWARE_UPDATE_FAIL {
        description "[Firmware Update Fail] logging type \"Firmware Update Fail\"";
        value 11;
      }
      enum LOGGING_TYPE_COLD_START {
        description "[Cold Start] logging type \"Cold Start\"";
        value 20;
      }
      enum LOGGING_TYPE_WARM_START {
        description "[Warm Start] logging type \"Warm Start\"";
        value 21;
      }
      enum LOGGING_TYPE_FACTORY_RESET {
        description "[Factory Reset] logging type \"Factory Reset\"";
        value 30;
      }
      enum LOGGING_TYPE_CONFIGURATION_LOADED {
        description "[Configuration Loaded] logging type \"Configuration Loaded\"";
        value 31;
      }
      enum LOGGING_TYPE_CHANGE_CONFIG {
        description "[Change Config] logging type \"Change Config\"";
        value 32;
      }
      enum LOGGING_TYPE_CHANGE_OFFLINE_CONFIG {
        description "[Change Offline Config] logging type \"Change Offline Config\"";
        value 33;
      }
      enum LOGGING_TYPE_LOGIN_SUCCESS {
        description "[Login Success] logging type \"Login Success\"";
        value 40;
      }
      enum LOGGING_TYPE_LOGIN_PASSWORD_ATTEMPT_FAIL {
        description "[Login Password Attempt Fail] logging type \"Login Password Attempt Fail\"";
        value 41;
      }
      enum LOGGING_TYPE_LOGIN_INTERFACE_ACCESS_DENIED {
        description "[Login Interface Access Denied] logging type \"Login Interface Access Denied\"";
        value 42;
      }
      enum LOGGING_TYPE_LOGIN_OUT {
        description "[Login Out] logging type \"Login Out\"";
        value 43;
      }
      enum LOGGING_TYPE_LINK_UP {
        description "[Link Up] logging type \"Link Up\"";
        value 50;
      }
      enum LOGGING_TYPE_LINK_DOWN {
        description "[Link Down] logging type \"Link Down\"";
        value 51;
      }
      enum LOGGING_TYPE_LINK_STATE_CHANGE {
        description "[Link State Change] logging type \"Link State Change\"";
        value 52;
      }
      enum LOGGING_TYPE_MAC_ACCEPTED {
        description "[MAC Accepted] logging type \"MAC Accepted\"";
        value 60;
      }
      enum LOGGING_TYPE_MAC_AUTH_ERROR {
        description "[MAC Auth Error] logging type \"MAC Auth Error\"";
        value 61;
      }
      enum LOGGING_TYPE_MAC_BLOCKED {
        description "[MAC Blocked] logging type \"MAC Blocked\"";
        value 62;
      }
      enum LOGGING_TYPE_MAC_BLOCKED_VLAN {
        description "[MAC Blocked Vlan] logging type \"MAC Blocked Vlan\"";
        value 63;
      }
      enum LOGGING_TYPE_MAC_TABLE_CHANGE {
        description "[MAC Table Change] logging type \"MAC Table Change\"";
        value 64;
      }
      enum LOGGING_TYPE_MAC_AUTH_REQUEST {
        description "[MAC Auth Request] logging type \"MAC Auth Request\"";
        value 65;
      }
      enum LOGGING_TYPE_MAC_CONFLICT {
        description "[MAC Conflict] logging type \"MAC Conflict\"";
        value 66;
      }
      enum LOGGING_TYPE_MAC_SECURITY_VIOLATION {
        description "[MAC Security Violation] logging type \"MAC Security Violation\"";
        value 67;
      }
      enum LOGGING_TYPE_MAC_LEARNING_OVER_LIMIT {
        description "[MAC Learning Over Limit] logging type \"MAC Learning Over Limit\"";
        value 68;
      }
      enum LOGGING_TYPE_MAC_TABLE_FULL {
        description "[MAC Table Full] logging type \"MAC Table Full\"";
        value 69;
      }
      enum LOGGING_TYPE_LOOP_REMOVED {
        description "[Loop Removed] logging type \"Loop Removed\"";
        value 80;
      }
      enum LOGGING_TYPE_LOOP_DETECTED {
        description "[Loop Detected] logging type \"Loop Detected\"";
        value 81;
      }
      enum LOGGING_TYPE_LACP_CONNECT {
        description "[Lacp Connect] logging type \"Lacp Connect\"";
        value 90;
      }
      enum LOGGING_TYPE_LACP_DISCONNECT {
        description "[Lacp Disconnect] logging type \"Lacp Disconnect\"";
        value 91;
      }
      enum LOGGING_TYPE_NTP_FAIL {
        description "[Ntp Fail] logging type \"Ntp Fail\"";
        value 100;
      }
      enum LOGGING_TYPE_NTP_SYNC {
        description "[Ntp Sync] logging type \"Ntp Sync\"";
        value 101;
      }
      enum LOGGING_TYPE_LLDP_POE_REQUEST {
        description "[Lldp PoE Request] logging type \"Lldp PoE Request\"";
        value 110;
      }
      enum LOGGING_TYPE_PACKET_INTERCEPTED {
        description "[Packet Intercepted] logging type \"Packet Intercepted\"";
        value 120;
      }
      enum LOGGING_TYPE_NETWORK_ATTACK {
        description "[Network Attack] logging type \"Network Attack\"";
        value 121;
      }
      enum LOGGING_TYPE_CLI_SCRIPT_EXECUTE_SUCCESS {
        description "[CLI Script Execute Success] logging type \"CLI Script Execute Success\"";
        value 130;
      }
      enum LOGGING_TYPE_CLI_SCRIPT_EXECUTE_FAIL {
        description "[CLI Script Execute Fail] logging type \"CLI Script Execute Fail\"";
        value 131;
      }
      enum LOOING_TYPE_MULTICAST_LEARNING_GROUP_OVER_LIMIT {
        description "[Multicast Group Learning Over Limit]";
        value 140;
      }
      enum LOGGING_TYPE_SFP_INSERTED {
        description "[SFP Inserted] logging type \"SFP Inserted\"";
        value 200;
      }
      enum LOGGING_TYPE_SFP_REMOVED {
        description "[SFP Removed] logging type \"SFP Removed\"";
        value 201;
      }
      enum LOGGING_TYPE_SFP_SIGNAL_PRESENT {
        description "[SFP Signal Present] logging type \"SFP Signal Present\"";
        value 202;
      }
      enum LOGGING_TYPE_SFP_SIGNAL_LOSS {
        description "[SFP Signal Loss] logging type \"SFP Signal Loss\"";
        value 203;
      }
      enum LOGGING_TYPE_SFP_SIGNAL_CHANGE {
        description "[SFP Signal Change] logging type \"SFP Signal Change\"";
        value 204;
      }
      enum LOGGING_TYPE_POE_CONNECT {
        description "[PoE Connect] logging type \"PoE Connect\"";
        value 210;
      }
      enum LOGGING_TYPE_POE_VOLTAGE {
        description "[PoE Voltage] logging type \"PoE Voltage\"";
        value 211;
      }
      enum LOGGING_TYPE_POE_ERROR {
        description "[PoE Error] logging type \"PoE Error\"";
        value 212;
      }
      enum LOGGING_TYPE_POE_DISCONNECT {
        description "[PoE Disconnect] logging type \"PoE Disconnect\"";
        value 213;
      }
      enum LOGGING_TYPE_POE_EMERGENCY_MODE_ON {
        description "[PoE Emergency Mode On] logging type \"PoE Emergency Mode On\"";
        value 214;
      }
      enum LOGGING_TYPE_POE_EMERGENCY_MODE_OFF {
        description "[PoE Emergency Mode Off] logging type \"PoE Emergency Mode Off\"";
        value 215;
      }
      enum LOGGING_TYPE_LED_CONTROL {
        description "[Led Control] logging type \"Led Control\"";
        value 220;
      }
      enum LOGGING_TYPE_BUTTON_PRESSED {
        description "[Button Pressed] logging type \"Button Pressed\"";
        value 221;
      }
      enum LOGGING_TYPE_HARDWARE_ERROR {
        description "[Hardware Error] logging type \"Hardware Error\"";
        value 222;
      }
      enum LOGGING_TYPE_TEMPERATURE_OK {
        description "[Temperature Ok] logging type \"Temperature Ok\"";
        value 230;
      }
      enum LOGGING_TYPE_TEMPERATURE_WARNING {
        description "[Temperature Warning] logging type \"Temperature Warning\"";
        value 231;
      }
      enum LOGGING_TYPE_TEMPERATURE_FAILURE {
        description "[Temperature Failure] logging type \"Temperature Failure\"";
        value 232;
      }
      enum LOGGING_TYPE_CPU_OK {
        description "[CPU Ok] logging type \"CPU Ok\"";
        value 233;
      }
      enum LOGGING_TYPE_CPU_WARNING {
        description "[CPU Warning] logging type \"CPU Warning\"";
        value 234;
      }
      enum LOGGING_TYPE_CPU_FAILURE {
        description "[CPU Failure] logging type \"CPU Failure\"";
        value 235;
      }
      enum LOGGING_TYPE_MEMORY_OK {
        description "[Memory Ok] logging type \"Memory Ok\"";
        value 236;
      }
      enum LOGGING_TYPE_MEMORY_WARNING {
        description "[Memory Warning] logging type \"Memory Warning\"";
        value 237;
      }
      enum LOGGING_TYPE_MEMORY_FAILURE {
        description "[Memory Failure] logging type \"Memory Failure\"";
        value 238;
      }
      enum LOGGING_TYPE_CABLE_CHANGE_DETECTED {
        description "[Cable Change Detected] logging type \"Cable Change Detected\"";
        value 240;
      }
      enum LOGGING_TYPE_CABLE_CONNECTION_ESTABLISHED {
        description "[Cable Connection Established] logging type \"Cable Connection Established\"";
        value 241;
      }
      enum LOGGING_TYPE_CABLE_CONNECTION_LOST {
        description "[Cable Connection Lost] logging type \"Cable Connection Lost\"";
        value 242;
      }
    }
  }
  // event/crypto.proto
  typedef CryptoTypeOptions {
    type enumeration {
      enum CRYPTO_TYPE_ENCODE {
        description "[Encode]";
        value 0;
      }
      enum CRYPTO_TYPE_DECODE {
        description "[Decode]";
        value 1;
      }
      enum CRYPTO_TYPE_MD5 {
        description "[MD5]";
        value 2;
      }
    }
  }
  // event/dhcp.proto
  typedef DHCPClientTypeOptions {
    type enumeration {
      enum DHCP_CLIENT_TYPE_V4_CHANGE {
        description "[V4 Change] V4 Change";
        value 0;
      }
      enum DHCP_CLIENT_TYPE_V6_CHANGE {
        description "[V6 Change] V6 Change";
        value 1;
      }
    }
  }
  // event/fdb.proto
  typedef FDBParameterTypeOptions {
    type enumeration {
      enum FDB_PARAMETER_TYPE_PORT_OVER {
        description "[Port Over]";
        value 0;
      }
      enum FDB_PARAMETER_TYPE_FDB_FULL {
        description "[FDB FUll]";
        value 1;
      }
    }
  }
  // event/initialize.proto
  typedef ServiceActionTypeOptions {
    type enumeration {
      enum SERVICE_ACTION_TYPE_START {
        description "[Start]";
        value 0;
      }
      enum SERVICE_ACTION_TYPE_END {
        description "[End]";
        value 1;
      }
    }
  }
  // event/layer.proto
  typedef EthernetTypeOptions {
    type enumeration {
      enum ETHERNET_TYPE_LLC {
        description "[LLC]";
        value 0;
      }
      enum ETHERNET_TYPE_IP_V4 {
        description "[IPv4]";
        value 2048;
      }
      enum ETHERNET_TYPE_ARP {
        description "[ARP]";
        value 2054;
      }
      enum ETHERNET_TYPE_CISCO_DISCOVERY {
        description "[Cisco Discovery]";
        value 8192;
      }
      enum ETHERNET_TYPE_DOT_1Q {
        description "[Dot1Q]";
        value 33024;
      }
      enum ETHERNET_TYPE_IP_V6 {
        description "[IPv6]";
        value 34525;
      }
      enum ETHERNET_TYPE_LACP {
        description "[Lacp]";
        value 34825;
      }
      enum ETHERNET_TYPE_EAPOL {
        description "[EAPOL]";
        value 34958;
      }
      enum ETHERNET_TYPE_LINK_LAYER_DISCOVERY {
        description "[Link Layer Discovery]";
        value 35020;
      }
      enum ETHERNET_TYPE_IEEE_1588 {
        description "[IEEE 1588]";
        value 35063;
      }
      enum ETHERNET_TYPE_USER_DEFINED {
        description "[User Defined]";
        value 65535;
      }
    }
  }
  // event/layer.proto
  typedef IPProtocolTypeOptions {
    type enumeration {
      enum IP_PROTOCOL_TYPE_IP_V6_HOPBYHOP {
        description "[IPv6 HopByHop]";
        value 0;
      }
      enum IP_PROTOCOL_TYPE_IGMP {
        description "[IGMP]";
        value 2;
      }
      enum IP_PROTOCOL_TYPE_IP_V4 {
        description "[IPv4]";
        value 4;
      }
      enum IP_PROTOCOL_TYPE_TCP {
        description "[TCP]";
        value 6;
      }
      enum IP_PROTOCOL_TYPE_UDP {
        description "[UDP]";
        value 17;
      }
      enum IP_PROTOCOL_TYPE_IP_V6 {
        description "[IPv6]";
        value 41;
      }
    }
  }
  // event/linkchange.proto
  typedef LinkTypeOptions {
    type enumeration {
      enum LINK_TYPE_UP {
        description "[Up] Link up";
        value 0;
      }
      enum LINK_TYPE_DOWN {
        description "[Down] Link down";
        value 1;
      }
    }
  }
  // event/login.proto
  typedef LoginResultTypeOptions {
    type enumeration {
      enum LOGIN_RESULT_TYPE_SUCCESS {
        description "[Success] login success";
        value 0;
      }
      enum LOGIN_RESULT_TYPE_LOADING_ACCESS_TOKEN {
        description "[Loading Access Token] loading access token";
        value 1;
      }
      enum LOGIN_RESULT_TYPE_PASSWORD_ATTEMPT_FAILED {
        description "[Password Attempt Failed] login failed due to wrong password";
        value 2;
      }
      enum LOGIN_RESULT_TYPE_INTERFACE_ACCESS_DENIED {
        description "[Interface Access Denied] the interface is forbidden for the current user login";
        value 3;
      }
      enum LOGIN_RESULT_TYPE_ATTEMPT_FAILED {
        description "[Attempt Failed] login attempt failed";
        value 4;
      }
    }
  }
  // event/login.proto
  typedef LoginTypeOptions {
    type enumeration {
      enum LOGIN_TYPE_LOGIN_LOCAL {
        description "[Login Local] local user login";
        value 0;
      }
      enum LOGIN_TYPE_LOGIN_RADIUS {
        description "[Login Radius] radius user account login";
        value 1;
      }
      enum LOGIN_TYPE_LOGIN_TACPLUS {
        description "[Login TACACS+] TACACS+ user account login";
        value 2;
      }
      enum LOGIN_TYPE_PACC_VIA_MAC_TABLE {
        description "[PACC Via MAC Table] PACC Via MAC Table";
        value 3;
      }
      enum LOGIN_TYPE_PACC_MAC_VIA_RADIUS {
        description "[PACC Mac Via Radius] PACC Mac Via Radius";
        value 4;
      }
      enum LOGIN_TYPE_PACC_802_1X_VIA_RADIUS {
        description "[PACC 802.1X Via Radius] PACC 802.1X Via Radius";
        value 5;
      }
      enum LOGIN_TYPE_PACC_VIA_MAC_EVENT_ONLY {
        description "[PACC Via Mac Event Only] PACC Via Mac Event Only";
        value 6;
      }
      enum LOGIN_TYPE_PACC_EDGE_802_1X_VIA_RADIUS {
        description "[PACC Edge 802.1X Via Radius] PACC Edge 802.1X Via Radius";
        value 7;
      }
    }
  }
  // event/login.proto
  typedef LoginInterfaceNameTypeOptions {
    type enumeration {
      enum LOGIN_INTERFACE_NAME_TYPE_SSH {
        description "[SSH] user login through SSH connection";
        value 0;
      }
      enum LOGIN_INTERFACE_NAME_TYPE_TELNET {
        description "[Telnet] user login through Telnet connection";
        value 1;
      }
      enum LOGIN_INTERFACE_NAME_TYPE_WEB {
        description "[WEB] user login through WEB connection";
        value 2;
      }
      enum LOGIN_INTERFACE_NAME_TYPE_SNMP {
        description "[SNMP] user login through SNMP connection";
        value 3;
      }
      enum LOGIN_INTERFACE_NAME_TYPE_FTP {
        description "[FTP] user login through FTP connection";
        value 4;
      }
      enum LOGIN_INTERFACE_NAME_TYPE_CONSOLE {
        description "[Console] user login through Console connection";
        value 5;
      }
    }
  }
  // event/maintenance.proto
  typedef MaintenanceActionTypeOptions {
    type enumeration {
      enum MAINTENANCE_ACTION_TYPE_SNAPSHOT {
        description "[Snapshot] Maintenance action type snapshot";
        value 0;
      }
      enum MAINTENANCE_ACTION_TYPE_FIRMWARE_UPGRADE_FAIL {
        description "[Firmware Upgrade Fail] Maintenance action type firmware upgrade fail";
        value 1;
      }
      enum MAINTENANCE_ACTION_TYPE_FIRMWARE_UPGRADE_SUCCESS {
        description "[Firmware Upgrade Success] Maintenance action type firmware upgrade success";
        value 2;
      }
      enum MAINTENANCE_ACTION_TYPE_CONFIG_IMPORT {
        description "[Config Import] Maintenance action type config import";
        value 3;
      }
      enum MAINTENANCE_ACTION_TYPE_CONFIG_EXPORT {
        description "[Config Export] Maintenance action type config export";
        value 4;
      }
    }
  }
  // event/multicast.proto
  typedef MulticastActionTypeOptions {
    type enumeration {
      enum MULTICAST_ACTION_TYPE_LEARNING_GROUP_OVER_LIMIT {
        description "[Group Over Limit]";
        value 0;
      }
    }
  }
  // event/poe.proto
  typedef PoEParameterTypeOptions {
    type enumeration {
      enum POE_PARAMETER_TYPE_BUDGET_MAX {
        description "[Budget MAX]";
        value 0;
      }
      enum POE_PARAMETER_TYPE_BUDGET_ENOUGH {
        description "[Budget Enough]";
        value 1;
      }
      enum POE_PARAMETER_TYPE_POE_CONNECT {
        description "[PoE Connect]";
        value 2;
      }
      enum POE_PARAMETER_TYPE_POE_DISCONNECT {
        description "[PoE Disconnect]";
        value 3;
      }
      enum POE_PARAMETER_TYPE_POE_ERROR {
        description "[PoE Error]";
        value 4;
      }
    }
  }
  // event/port.proto
  typedef PortSpeedDuplexTypeOptions {
    type enumeration {
      enum PORT_SPEED_DUPLEX_TYPE_AUTO {
        description "[Auto]";
        value 0;
      }
      enum PORT_SPEED_DUPLEX_TYPE_10M_FULL {
        description "[10 Mbps / Full]";
        value 1;
      }
      enum PORT_SPEED_DUPLEX_TYPE_100M_FULL {
        description "[100 Mbps / Full]";
        value 3;
      }
      enum PORT_SPEED_DUPLEX_TYPE_1000M_FULL {
        description "[1 Gbps  / Full]";
        value 5;
      }
      enum PORT_SPEED_DUPLEX_TYPE_2500M_FULL {
        description "[2.5 Gbps / Full]";
        value 6;
      }
      enum PORT_SPEED_DUPLEX_TYPE_5G_FULL {
        description "[5 Gbps / Full]";
        value 7;
      }
      enum PORT_SPEED_DUPLEX_TYPE_10G_FULL {
        description "[10 Gbps / Full]";
        value 8;
      }
      enum PORT_SPEED_DUPLEX_TYPE_25G_FULL {
        description "[25 Gbps / Full]";
        value 9;
      }
      enum PORT_SPEED_DUPLEX_TYPE_40G_FULL {
        description "[40 Gbps / Full]";
        value 10;
      }
      enum PORT_SPEED_DUPLEX_TYPE_100G_FULL {
        description "[100 Gbps / Full]";
        value 11;
      }
      enum PORT_SPEED_DUPLEX_TYPE_NA {
        description "[NA]";
        value 12;
      }
    }
  }
  // event/sfp.proto
  typedef SFPActionTypeOptions {
    type enumeration {
      enum SFP_ACTION_TYPE_INSERTED {
        description "[Inserted] Inserted";
        value 0;
      }
      enum SFP_ACTION_TYPE_REMOVED {
        description "[Removed] Removed";
        value 1;
      }
      enum SFP_ACTION_TYPE_SIGNAL_FAULT {
        description "[Signal Fault] Signal fault";
        value 2;
      }
      enum SFP_ACTION_TYPE_SIGNAL_LOSS {
        description "[Signal Loss] Signal loss";
        value 3;
      }
    }
  }
  // event/sfp.proto
  typedef SFPStatusTypeOptions {
    type enumeration {
      enum SFP_STATUS_TYPE_UNKNOWN {
        description "[Unknown] This is show when no data could be retrieved.";
        value 0;
      }
      enum SFP_STATUS_TYPE_OK {
        description "[Ok] Optical operation conditions are OK.";
        value 1;
      }
      enum SFP_STATUS_LASER_TYPE_DISABLED {
        description "[Disabled] Laser is disabled. No data can be sent. The port may be disabled.";
        value 2;
      }
      enum SFP_STATUS_TYPE_LOSS_OF_SIGNAL {
        description "[Loss Of Signal] This flag is set when the optical receive power level is below the critical lower limit.";
        value 3;
      }
      enum SFP_STATUS_TYPE_READ_ERROR {
        description "[Read Error] Management read access to the SFP has failed.";
        value 4;
      }
    }
  }
  // event/sfp.proto
  typedef SFPTypeOptions {
    type enumeration {
      enum SFP_TYPE_EMPTY {
        description "[Empty] No SFP is inserted.";
        value 0;
      }
      enum SFP_TYPE_UNKNOWN {
        description "[Unknown] An SFP is inserted but its type could not be decoded.";
        value 1;
      }
      enum SFP_TYPE_OR_PLUS {
        description "[Or Plus] A normal SFP or SFP+ is inserted.";
        value 2;
      }
      enum SFP_TYPE_GBIC {
        description "[Gbic] A GBIC is inserted.";
        value 3;
      }
      enum SFP_TYPE_SFF {
        description "[Sff] An SFF fixed optical interface is installed.";
        value 4;
      }
    }
  }
  // event/sfp.proto
  typedef SFPConnectorTypeOptions {
    type enumeration {
      enum SFP_CONNECTOR_TYPE_UNKNOWN {
        description "[Unknown] Connector type cannot be decoded.";
        value 0;
      }
      enum SFP_CONNECTOR_TYPE_LC {
        description "[Lc] LC connector is used.";
        value 1;
      }
      enum SFP_CONNECTOR_TYPE_SC {
        description "[Sc] SC connector is used.";
        value 2;
      }
      enum SFP_CONNECTOR_TYPE_MT_RJ {
        description "[Mt Rj] MT_RJ connector is used.";
        value 3;
      }
      enum SFP_CONNECTOR_TYPE_RJ45 {
        description "[Rj45] Electrical RJ45 connector is used.";
        value 4;
      }
      enum SFP_CONNECTOR_TYPE_MU {
        description "[Mu] MU connector is used.";
        value 5;
      }
    }
  }
  // event/stormcontrol.proto
  typedef StormcontrolActionTypeOptions {
    type enumeration {
      enum STORMCONTROL_ACTION_TYPE_PORT_NORMAL {
        description "[Normal] the port is normal";
        value 0;
      }
      enum STORMCONTROL_ACTION_TYPE_PORT_SHUTDOWN {
        description "[Shutdown] the port is shutdown";
        value 1;
      }
      enum STORMCONTROL_ACTION_TYPE_PORT_BLOCKING {
        description "[Blocking] the port is blocking";
        value 2;
      }
    }
  }
  // event/system.proto
  typedef NTPActionTypeOptions {
    type enumeration {
      enum NTP_ACTION_TYPE_FAIL {
        description "[Fail] Fail";
        value 0;
      }
      enum NTP_ACTION_TYPE_SYNC {
        description "[Sync] Sync";
        value 1;
      }
    }
  }
  // event/system.proto
  typedef BootActionTypeOptions {
    type enumeration {
      enum BOOT_ACTION_TYPE_WARM_START {
        description "[Warm Start] Warm Start";
        value 0;
      }
      enum BOOT_ACTION_TYPE_COLD_START {
        description "[Cold Start] Cold Start";
        value 1;
      }
      enum BOOT_ACTION_TYPE_READY {
        description "[Ready] Ready";
        value 2;
      }
      enum BOOT_ACTION_TYPE_PORT_READY {
        description "[Port Ready] Port Ready";
        value 3;
      }
    }
  }
  // event/system.proto
  typedef NetworkIPv6TypeOptions {
    type enumeration {
      enum IPV6_TYPE_LINK_LOCAL {
        description "[Link Local] Ipv6 type link local";
        value 0;
      }
      enum IPV6_TYPE_VIRTUAL_LINK_LOCAL {
        description "[Virtual Link Local] Ipv6 type virtual link local";
        value 1;
      }
      enum IPV6_TYPE_UNICAST {
        description "[Unicast] Ipv6 type unicast";
        value 2;
      }
    }
  }
  // event/udld.proto
  typedef UdldActionTypeOptions {
    type enumeration {
      enum UDLD_ACTION_PORT_SHUTDOWN {
        description "[Shutdown] the port is shutdown";
        value 0;
      }
    }
  }
  // event/vlan.proto
  typedef VLANParameterTypeOptions {
    type enumeration {
      enum VLAN_PARAMETER_TYPE_MANAGMENT_ADD {
        description "[Managment Add]";
        value 0;
      }
      enum VLAN_PARAMETER_TYPE_MANAGMENT_DELETE {
        description "[Managment Delete]";
        value 1;
      }
      enum VLAN_PARAMETER_TYPE_UNAUTH_VLAN_CHANGE {
        description "[UnAuth Change]";
        value 2;
      }
    }
  }
  // event/event.proto
  typedef ListenTypeOptions {
    type enumeration {
      enum LISTEN_TYPE_TX {
        description "[Tx] Listen type tx";
        value 0;
      }
      enum LISTEN_TYPE_RX {
        description "[Rx] Listen type rx";
        value 1;
      }
      enum LISTEN_TYPE_BOTH {
        description "[Both] Listen type both";
        value 2;
      }
    }
  }
  // event/event.proto
  typedef InternalTypeOptions {
    type enumeration {
      enum INTERNAL_TYPE_ALL {
        description "[All] Internal type all";
        value 0;
      }
      enum INTERNAL_TYPE_SERVICE {
        description "[Service] Internal type service";
        value 1;
      }
      enum INTERNAL_TYPE_HARDWARE {
        description "[Hardware] Internal type hardware";
        value 10;
      }
      enum INTERNAL_TYPE_LED {
        description "[Led] Internal type led";
        value 11;
      }
      enum INTERNAL_TYPE_POE {
        description "[Poe] Internal type poe";
        value 12;
      }
      enum INTERNAL_TYPE_SFP {
        description "[Sfp] Internal type sfp";
        value 13;
      }
      enum INTERNAL_TYPE_CABLE {
        description "[Cable] Internal type cable";
        value 14;
      }
      enum INTERNAL_TYPE_PORT {
        description "[Port] Internal type port";
        value 15;
      }
      enum INTERNAL_TYPE_BUTTON {
        description "[Button] Internal type button";
        value 16;
      }
      enum INTERNAL_TYPE_LOGIN {
        description "[Login] Internal type login";
        value 20;
      }
      enum INTERNAL_TYPE_SCRIPT {
        description "[Script] Internal type script";
        value 21;
      }
      enum INTERNAL_TYPE_SYSTEM {
        description "[System] Internal type system";
        value 22;
      }
      enum INTERNAL_TYPE_MAINTENANCE {
        description "[Maintenance] Internal type maintenance";
        value 23;
      }
      enum INTERNAL_TYPE_NTP {
        description "[Ntp] Internal type ntp";
        value 24;
      }
      enum INTERNAL_TYPE_LINK {
        description "[Link] Internal type link";
        value 25;
      }
      enum INTERNAL_TYPE_NETWORK {
        description "[Network] Internal type network";
        value 26;
      }
      enum INTERNAL_TYPE_BOOT {
        description "[Boot] Internal type boot";
        value 27;
      }
      enum INTERNAL_TYPE_MONITOR {
        description "[Monitor] Internal type monitor";
        value 28;
      }
      enum INTERNAL_TYPE_PORTAUTH {
        description "[Portauth] Internal type portauth";
        value 40;
      }
      enum INTERNAL_TYPE_G8032RING {
        description "[G8032 Ring] Internal type g8032 ring";
        value 41;
      }
      enum INTERNAL_TYPE_AGGREGATION {
        description "[Aggregation] Internal type aggregation";
        value 42;
      }
      enum INTERNAL_TYPE_LOOP {
        description "[Loop] Internal type loop";
        value 43;
      }
      enum INTERNAL_TYPE_LLDP {
        description "[Lldp] Internal type lldp";
        value 44;
      }
      enum INTERNAL_TYPE_CDP {
        description "[Cdp] Internal type cdp";
        value 45;
      }
      enum INTERNAL_TYPE_VLAN {
        description "[Vlan] Internal type vlan";
        value 46;
      }
      enum INTERNAL_TYPE_DHCP {
        description "[Dhcp] Internal type dhcp";
        value 47;
      }
      enum INTERNAL_TYPE_IGMP {
        description "[Igmp] Internal type igmp";
        value 48;
      }
      enum INTERNAL_TYPE_MLD {
        description "[Mld] Internal type mld";
        value 49;
      }
      enum INTERNAL_TYPE_FDB {
        description "[Fdb] Internal type fdb";
        value 50;
      }
      enum INTERNAL_TYPE_AU {
        description "[Au] Internal type au";
        value 51;
      }
      enum INTERNAL_TYPE_ACL {
        description "[Acl] Internal type acl";
        value 52;
      }
      enum INTERNAL_TYPE_TIMERANGE {
        description "[Timerange] Internal type timerange";
        value 53;
      }
      enum INTERNAL_TYPE_STORMCONTROL {
        description "[Stormcontrol] Internal type stormcontrol";
        value 54;
      }
      enum INTERNAL_TYPE_UDLD {
        description "[Udld] Internal type UDLD";
        value 55;
      }
      enum INTERNAL_TYPE_TEST {
        description "[Test] Internal type test";
        value 90;
      }
      enum INTERNAL_TYPE_API {
        description "[Api] Internal type api";
        value 91;
      }
      enum INTERNAL_TYPE_DEBUG {
        description "[Debug] Internal type debug";
        value 99;
      }
    }
  }
  // event/target.proto
  typedef TargetLogTypeOptions {
    type enumeration {
      enum TARGET_LOG_TYPE_DISABLED {
        description "[Disabled] This logging entry is disabled";
        value 0;
      }
      enum TARGET_LOG_TYPE_SYSLOG {
        description "[Syslog] The event will be forwarded as Syslog";
        value 1;
      }
      enum TARGET_LOG_TYPE_SNMP_TRAP_V1 {
        description "[Snmp Trap V1] The event will be forwarded as SNMP trap using SNMP V1 format";
        value 2;
      }
      enum TARGET_LOG_TYPE_SNMP_TRAP_V2C {
        description "[Snmp Trap V2C] The event will be forwarded as SNMP trap using SNMP V2c format";
        value 3;
      }
      enum TARGET_LOG_TYPE_SNMP_TRAP_V3 {
        description "[Snmp Trap V3] The event will be forwarded as SNMP trap using SNMP V3 format";
        value 4;
      }
      enum TARGET_LOG_TYPE_SNMP_INFORM_V2C {
        description "[Snmp Inform V2 C] The event will be forwarded as SNMP trap using SNMP V2c acknowledged Inform format";
        value 5;
      }
      enum TARGET_LOG_TYPE_SNMP_INFORM_V3 {
        description "[Snmp Inform V3] The event will be forwarded as SNMP trap using SNMP V3 acknowledged Inform format";
        value 6;
      }
      enum TARGET_LOG_TYPE_DISPLAY_IN_CLI {
        description "[Display In Cli] The event will be shown to all currently open terminal sessions";
        value 7;
      }
      enum TARGET_LOG_TYPE_DISPLAY_IN_WEB {
        description "[Display In Web] The event will be shown to all currently open web sessions";
        value 9;
      }
    }
  }
  // event/target.proto
  typedef LoggingSeverityTypeOptions {
    type enumeration {
      enum LOGGING_SEVERITY_TYPE_DISABLED {
        description "[Disabled] Syslog output to this target is disabled";
        value 0;
      }
      enum LOGGING_SEVERITY_TYPE_DEBUG {
        description "[Debug] Internal system debugging information";
        value 1;
      }
      enum LOGGING_SEVERITY_TYPE_INFO {
        description "[Info] Information with no important consequences";
        value 2;
      }
      enum LOGGING_SEVERITY_TYPE_NOTICE {
        description "[Notice] Notification about normal occurrence";
        value 3;
      }
      enum LOGGING_SEVERITY_TYPE_WARNING {
        description "[Warning] Warning about a normal problem";
        value 4;
      }
      enum LOGGING_SEVERITY_TYPE_ERROR {
        description "[Error] Unexpected error has occurred";
        value 5;
      }
      enum LOGGING_SEVERITY_TYPE_CRITICAL {
        description "[Critical] Critical error which compromises data traffic or stability";
        value 6;
      }
      enum LOGGING_SEVERITY_TYPE_ALERT {
        description "[Alert] Very important error condition";
        value 7;
      }
      enum LOGGING_SEVERITY_TYPE_EMERGENCY {
        description "[Emergency] Highest possible error condition (no set by this product)";
        value 8;
      }
    }
  }
}
