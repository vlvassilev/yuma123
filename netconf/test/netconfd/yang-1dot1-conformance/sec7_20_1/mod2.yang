module mod2 {
  namespace "http://yuma123.org/ns/sec7_20_1/mod2";
  prefix m2;

  feature "foo";

  feature "bar";

  container foobar {
    if-feature "foo or bar";
    presence "foo or bar is on";
  }
}
