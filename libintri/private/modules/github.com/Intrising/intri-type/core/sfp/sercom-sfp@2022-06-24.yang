module sercom-sfp {

  namespace "sercom:sercom-sfp";
  prefix "sercom-sfp";
  organization "
    Sercomm Inc.";
  contact "
    sercomm@sercomm.com.tw";
  revision 2022-06-24 {
    description "Build date.";
  }

  import sercom-event {
    prefix sercom-event;
  }
  import sercom-empty {
    prefix sercom-empty;
  }
  grouping Config {
    leaf LossOfSignalEvent {
      mandatory "true";
      type boolean;
    }
  }
  grouping Info {
    container List {
      list List_Entry {
        uses sercom-event:SFPInfo;
      }
    }
  }
  rpc sercom-sfp-SFP-GetConfig {
    output {
      uses Config;
    }
  }
  rpc sercom-sfp-SFP-SetConfig {
    input {
      uses Config;
    }
  }
  rpc sercom-sfp-SFP-GetStatus {
    output {
      uses Info;
    }
  }
}
