module device_test { 

    namespace "http://netconfcentral.org/ns/device_test";
    prefix "dt";
                
    revision 2011-09-07 {
        description "Initial revision.";
    }

    grouping resourceDescription {
        description "Common description of resources.";
        list resourceNode {
            key id;

            leaf id {
                description "Unique ID for the resource.";
                type uint32;
            }

            leaf resourceType {
                description "Type identifier for resource.";
                type uint32;
            }

            leaf configuration {
                description "Base-64 encoded binary configuration.";
                type binary;
            }

            leaf statusConfig {
                description "Base-64 encoded binary configuration of status 
                             reporting.";
                type binary;
            }

            leaf alarmConfig {
                description "Base-64 encoded binary configuration of alarm 
                             reporting.";
                type binary;
            }

            leaf physicalPath {
                description "Fixed physical path for the resource.";
                type string;
            }
        }
    }
    
    container part1 {
        presence "";
        description "Top-level container for part related items.";
        
        container part1Version {
            description "The top-level package version for all items contained
                         in this part.";
            config false;
            
            leaf packageVersion {
                type string;
            }             
            
            leaf packageValid {
                description "Indicates if this package version is valid.";
                type boolean;
            }
        }
        
        typedef permission1Type {
            description "Describes the type of the permission.";
            type enumeration {
                enum permanent {
                    description "The permission has no expiry time.";
                }
                enum elapsedTime {
                    description "The permission is valid for a specified period of 
                                 time since the permission was applied.";
                }
                enum runTime {
                    description "The permission has a specified amount of time for 
                                 which the permission can be used.";
                }
            }
        }
        
        container permission1Information {
            description "Contains a list of permission features.
                         The list will only contain those permissions that have
                         been loaded on to the device, including elapsedTime
                         and runTime permissions that have expired unless they
                         have been renewed.";
            
            config false;
            
            list permission1s {
                key id;
                leaf id {
                    description "The ID number of the permission.";
                    type uint32;
                }
                
                leaf name {
                    description "The name of the permission.";
                    type string;
                }
                
                leaf quantity {
                    description "The number of these permissions enabled.";
                    type uint32;
                }
                
                leaf typeOfPermission1 {
                    description "The type of this permission.";
                    type permission1Type;
                }
                                
                leaf timeUntilExpiry {
                    description "Number of minutes until the permission expires.";
                    type uint32;
                    units "minutes";
                }
                
                leaf permissionActive {
                    description "Indicates if this permission is currently active.";
                    type boolean;
                }               
            }
        }

        container notificationListeners {
            leaf-list statusListeners {
                description "List of IP addresses to send status messages to.";
                type uint32;
            }
            
            leaf-list snmpTrapListeners {
                description "List of IP addresses to send SNMP traps to.";
                type uint32;
            }
            
            container redundantPart1 {
                description "Network details for the redundant part.";
                leaf ipAddress {
                    type uint32;
                }
                
                leaf destinationProfile {
                    description "The profile number to be used by the redundant 
                                 part.";
                    type uint32;
                }
                
                leaf echoConfiguration {
                    description "Indicates if configuration changes are to be
                                 sent to the redundant part.";
                    type boolean;
                }
            }
        }
        
        uses resourceDescription;
        
        list socket1 {
            key id;
            leaf id {
                type uint32;
            }
            
            typedef itemType {
                description "Identifies what type of item has a version number.";
                type enumeration {
                    enum type1 {
                        description "An item of type 1.";
                    }
                    enum type2 {
                        description "An item of type 2.";
                    }
                    enum type3 {
                        description "An item of type 3.";
                    }
                }
            }
            
            grouping versionInformation {
                description "Version information for an item.";
                leaf itemDescription {
                    description "A description of the item.";
                    type string;
                }
                
                leaf versionNumber {
                    description "The version number of the item.";
                    type string;
                }
                
                leaf itemType {
                     description "The type of the item.";
                     type itemType;
                }
                
                leaf valid {
                    description "Indicates that the item is valid.";
                    type boolean;
                }
            }
            
            grouping part2VersionInformation {
                description "Version information of a part.";
                leaf name {
                    description "Name of the part.";
                    type string;
                }
                
                leaf sNumber {
                    description "The S number of the part.";
                    type string;
                }
                
                leaf packageVersion {
                    description "Overall version of this part.";
                    type string;
                }
                
                leaf packageValid {
                    description "Indicates if this collection is valid 
                                 on this part.";
                    type boolean;
                }
        
                leaf pcbModificationState {
                    description "The modification state of the part.";
                    type string;
                }
                
                leaf serialNumber {
                    description "The serial number of the part.";
                    type string;
                }
                
                list version {
                    description "Container for the version numbers for the items 
                                 on the part.";
                    key id;
                    
                    leaf id {
                        description "The ID number for this item.";
                        type uint32;
                    }
                    
                    uses versionInformation;
                }
            }
            
            grouping assemblyVersions {
                description "Version numbers for an assembly.";
                list part2 {
                    description "Container for the part version numbers.";
                    key id;
                    
                    leaf id {
                        description "The ID number for this item.";
                        type uint32;
                    }
        
                    uses part2VersionInformation;
                    list daughterPart2 {
                        description "Container for daughter part version 
                                     numbers.";
                        key id;
                        
                        leaf id {
                            description "The ID number of the daughter part.";
                            type uint32;
                        }
                        
                        uses part2VersionInformation;
                    }
                }
            }

            container socket1Version {
	            description "Version information of the part in this socket.";
	            config false;
	            uses assemblyVersions;
	        }
	        uses resourceDescription;
        }

	    container identification {
	        leaf unitLocation {
	           description "User definable location of this unit.
	                        This maps to SNMP system.sysLocation.";
	           type string; 
	        }
	
	        leaf unitName {
	           description "User definable name of this unit.
	                        This maps to SNMP system.sysName.";
	           type string; 
	        }
	   }
    }
    
    container xpo {
        presence "Indicates that the device test API is available.";
        description "Top-level container for all configuration and status 
                     objects.";

        ////////////////////////////////////
        // Start of main configuration block
        ////////////////////////////////////                        
        grouping connectionItem {
            description "Connection container.";

            leaf sourceId {
                description "The ID of the item providing the input to the 
                             connection.";
                type uint32;
            }

            leaf sourcePinId {
                description "The pin ID of the source item to use.";
                type uint32;
            }

            leaf destinationId {
                description "The ID of the item accepting the output of the 
                             connection.";
                type uint32;
            }

            leaf destinationPinId {
                description "The pin ID of the destination item out to use.";
                type uint32;
            }
            
            leaf bitrate {
                description "The maximum expected bitrate over this connection.";
                type uint32;
                units "bps";
            }
        }

        grouping streamItem {
            description "Stream container.";
            uses resourceDescription;

            list resourceConnection {
                description "Connection between two virtual resources.";
                key id;

                leaf id {
                    description "Connection identifier.";
                    type uint32;
                }
                uses connectionItem;
            }
        }
        
        list profile {
            key id;
            description "Profile container.";

            leaf id {
                description "Unique ID for this profile.";
                type uint32;
            }

            list stream {
                description "Stream container.";
                key id;

                leaf id {
                    description "Connection identifier.";
                    type uint32;
                }
                uses streamItem;
            }
            
            list streamConnection {
                description "Connection between two streams.";
                key id;

                leaf id {
                    description "Connection identifier.";
                    type uint32;
                }

                leaf sourceStreamId {
                    description "The ID of the stream providing the input to the
                                 connection.";
                    type uint32;
                }

                leaf destinationStreamId {
                    description "The ID of the stream accepting the output of the
                                 connection.";
                    type uint32;
                }

                uses connectionItem;
            }
        }

        leaf activeProfile {
            description "The number of the active profile.";
            type uint32;
        }
    }

    ///////////////////////////////////////////////////////////////////////////
    // Start of RPC block
    ///////////////////////////////////////////////////////////////////////////
    rpc get-resource-types {
        description "Obtains a list of available resource types.";

        output {
            leaf-list resource-type {
                description "The resource type present in system.";
                type uint32;
            }
        }
    }

    rpc get-resource-capability {
        description "Obtains the capabilities of a specific resource type.";

        input {
            leaf resource-type {
                description "The resource type to query.";
                type uint32;
            }
        }

        output {
            leaf resource-capability {
                description "Capabilities of resource.";
                type string;
            }
        }
    }

    typedef rpcResult {
        description "Result codes for XPO3 RPCs.";
        
        type enumeration {
            enum success {
                description "The operation was successful.";
            }
            enum invalidSourceProfileId {
                description "The operation failed due to the source 
                             profile ID being invalid.";
            }
            enum invalidDestinationProfileId {
                description "The operation failed due to the destination 
                             profile ID being invalid.";
            }
            enum invalidDestinationStreamId {
                description "The operation failed due to the destination 
                             stream ID being invalid.";
            }
            enum overwriteFailed {
                description "The operation failed because there was a 
                             pre-existing profile or stream in the requested 
                             destination, and the replace existing flag was set 
                             to false.";
            }
            enum routingFailed {
                description "As the result of a copy of modify operation, the
                             profile can no longer be routed.";
            }
            enum validationFailed {
                description "As the result of a copy of modify operation, the
                             profile can no longer be validated.";
            }
            enum invalidTime {
                description "The time specified was invalid or could not be
                             parsed.";
            }
            enum unknownLanguage {
                description "The language specified is unknown.";
            }
            enum dictionaryReferenceNotFound {
                description "The dicitionary reference requested was not found.";
            }
        }
    }
    
    rpc get-dictionary {
        description "Obtains the system dictionary.";
        
        input {
            leaf language {
                description "The language required.";
                type string;
            }
        }
        
        output {
            leaf getDictionaryResult {
                description "The result of the get operation.";
                type rpcResult;
            }

            leaf dictionary {
                description "The requested dictionary.";
                type string;
            }
        }    
    }
    
    rpc get-dictionary-reference {
        description "Get a specific dictionary reference.";
        
        input {
            leaf language {
                description "The language required.";
                type string;
            }
            
            leaf referenceId {
                description "The reference id required.";
                type uint32;
            }
        }    
        
        output {
            leaf getDictionaryReferenceResult {
                description "The result of the get operation.";
                type rpcResult;
            }

            leaf definition {
                description "The text matching the input request.";
                type string;
            }
        }
    }
        
    rpc copy-profile {
        description "Allows a profile to be copied.";
        
        input {
            leaf sourceProfileId {
                description "The ID of the profile to copy.";
                type uint32;
            }
            
            leaf destinationProfileId {
                description "The ID to copy the profile to.";
                type uint32;
            }
            
            leaf replaceExisting {
                description "Indicates if the copy operation is able to 
                             replace an existing profile.";
                type boolean;
            }
        }
        
        output {
            leaf copyResult {
                description "The result of the copy operation.";
                type rpcResult;
            }
        }
    }
    
    rpc copy-stream {
        description "Allows a stream to be copied.";
        
        input {
            leaf sourceProfileId {
                description "The ID of the profile that contains the 
                             stream to copy.";
                type uint32;
            }
            
            leaf sourceStreamId {
                description "The ID of the stream to copy.";
                type uint32;
            }
            
            leaf destinationProfileId {
                description "The profile to copy the stream in to.";
                type uint32;
            }
            
            leaf-list destintionStreamIdList {
                description "A list of stream IDs to copy to.";
                type uint32;
            }
            
            leaf replaceExisting {
                description "Indicates if the copy operation is able to 
                             replace an existing stream.  If any of the 
                             destination streams already exist the entire
                             copy operation is aborted, and no streams
                             are copied if this value is set to false.";
                type boolean;
            }
        }
        
        output {
            leaf copyResult {
                description "The result of the copy operation.";
                type rpcResult;
            }
        }
    }

    rpc modify-stream-config {
        description "Allows mass adjustment of the same parameters across many
                     streams within a single profile.";
        input {
            leaf profileId {
                description "The ID of the profile to be modified.";
                type uint32;
            }
            
            leaf-list streamIdList {
                description "A list of stream IDs to be modified.";
                type uint32;
            }
            
            leaf resourceNodeId {
                description "The ID of the resource node to be modified.";
                type uint32;
            }
            
            leaf configBitMask {
                description "A bit mask indicating which configuration items 
                             are to be modified.";
                type binary;
            }
            
            leaf configuration {
                description "The base-64 encoded configuration blob containing
                             only those items detailed by the configBitMask.";
                type binary;
            }
        }
        
        output {
            leaf editStreamConfigResult {
                description "The result of the edit config operation.";
                type rpcResult;
            }
        }       
    }
       
    rpc modify-stream-alarm-config {
        description "Allows mass adjustment of the same alarm configuration 
                     parameters across many  streams within a single profile.";
        input {
            leaf profileId {
                description "The ID of the profile to be modified.";
                type uint32;
            }
            
            leaf-list streamIdList {
                description "A list of stream IDs to be modified.";
                type uint32;
            }
            
            leaf resourceNodeId {
                description "The ID of the resource node to be modified.";
                type uint32;
            }
            
            leaf alarmConfigBitMask {
                description "A bit mask indicating which alarm configuration 
                             items are to be modified.";
                type binary;
            }
            
            leaf alarmConfig {
                description "The base-64 encoded alarm configuration blob 
                             containing only those items detailed by the 
                             alarmConfigBitMask.";
                type binary;
            }
        }
        
        output {
            leaf editStreamAlarmConfigResult {
                description "The result of the edit alarm config operation.";
                type rpcResult;
            }
        }       
    }

    rpc modify-stream-status-config {
        description "Allows mass adjustment of the same status configuration 
                     parameters across many streams within a single profile.";
        input {
            leaf profileId {
                description "The ID of the profile to be modified.";
                type uint32;
            }
            
            leaf-list streamIdList {
                description "A list of stream IDs to be modified.";
                type uint32;
            }
            
            leaf resourceNodeId {
                description "The ID of the resource node to be modified.";
                type uint32;
            }
            
            leaf statusConfigBitMask {
                description "A bit mask indicating which status configuration 
                             items are to be modified.";
                type binary;
            }
            
            leaf statusConfig {
                description "The base-64 encoded status configuration blob 
                             containing only those items detailed by the 
                             statusConfigBitMask.";
                type binary;
            }
        }
        
        output {
            leaf editStreamStatusConfigResult {
                description "The result of the edit status config operation.";
                type rpcResult;
            }
        }       
    }

    rpc get-status {
        description "Allows the status of given virtual resource to be 
                     retrieved.";
        
        input {
            leaf streamId {
                description "The stream ID of the virtual resource whose status 
                             is being requested.";
                type uint32;
            }
            
            leaf virtualResourceId {
                description "The ID of the virtual resource whose status is 
                             being requested.";
                type uint32;
            }
            
            leaf statusId {
                description "The ID of the status item being requested.";
                type uint32;
            }
        }
        
        output {
            leaf getStatusResult {
                description "Indicates if the get status operation was 
                             successful or not.";
                type rpcResult;
            }

            leaf statusValue {
                description "Base64 encoded value of the requested status item.";
                type string;
            }
        }
    }
    
    rpc get-time {
        description "Returns the current time.";
        
        output {
            leaf time {
                description "The current time as XML.";
                type string;
            }
        }
    }
    
    rpc set-time {
        description "Sets the current time.";
        
        input {
            leaf time {
                description "XML of the required time to be set.";
                type string;
            }
        }
        
        output {
            leaf setTimeResult {
                description "Result of the set time operation.";
                type rpcResult;
            }
        }
    }
}
