// Code generated by protoc-gen-yang. DO NOT EDIT.


/* ****************************************************************************************************
 * Import Path : "google.golang.org/genproto/googleapis/type/timeofday"                               *
 * Dir Path    : google.golang.org/genproto/googleapis/type/timeofday                                 *
 * Go Package  : timeofday                                                                            *
 * Files       : 1                                                                                    *
 **************************************************************************************************** */
module intri-timeofday {

  namespace "intri:intri-timeofday";

  prefix "intri-timeofday";

  organization "Intrising Inc.";

  contact "intrising@intrising.com.tw";

  revision 2022-06-23 {
    description "Build date.";
  }


  /* **************************************************************************************************
   * Msgs        : 1                                                                                  *
   ************************************************************************************************** */
  /* google/type/timeofday.proto */
  grouping TimeOfDay {
    leaf Hours {
      type int32;
    }
    leaf Minutes {
      type int32;
    }
    leaf Seconds {
      type int32;
    }
    leaf Nanos {
      type int32;
    }
  }

}
