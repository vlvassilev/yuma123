module test-xpath-re-match-concat {
  yang-version 1.1;

  namespace "http://yuma123.org/ns/test-xpath-re-match-concat";
  prefix trmc;

  import ietf-interfaces {
    prefix if;
  }

  organization
    "yuma123";

  description
    "Part of the xpath-re-match test - concat.";

  revision 2021-06-13 {
    description
      "Initial.";
  }
  leaf if-special-prefix {
    type string;
  }

  augment "/if:interfaces/if:interface" {
    leaf if-special-param {
      type uint32;
      must 're-match(../if:name, concat(/trmc:if-special-prefix, "\.\d+"))';
    }
  }
}
