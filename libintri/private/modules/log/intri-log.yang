module intri-log {
  namespace "intri:intri-log";
  prefix "intri-log";
  import logpb {
    prefix "logpb";
  }
  organization "Intrising Inc.";
  contact "xxx@intrising.com.tw";
  revision 2022-06-14 {
    description "Build date.";
  }
}
