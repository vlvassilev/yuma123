module netconfd {

    namespace "http://netconfcentral.com/ns/netconfd";

    prefix "nd";

    import ncx { prefix ncx; }

    import ncxtypes { prefix nt; }

    import netconf { prefix nc; }

    import xsd { prefix xs; }

    import smi { prefix smi; }

    organization  "Netconf Central";

    contact "Andy Bierman <support@netconfcentral.com>.";

    description "NCX Agent Configuration Parameters and Statistics";

    revision 2008-08-01 {
       description "Initial conversion from netconfd.ncx v 0.6";
    }

    container netconfd {
      description
         "
          Agent CLI for the NETCONF protocol.

          Usage:
            netconfd [parameters]
         ";

      leaf datapath {
        description
           "Internal file search path for config files.";
        type NcPathList;
      }

      leaf help {
        description
	  "Print netconfd help text and exit";
        type empty;
      }

      leaf log {
	description
	 "Full or relative filespec for the logfile to use instead of 
          logging agent output to STDOUT.";
        type string;
      }

      leaf log-append {
        description
          "If present, then append to the existing logfile,
           otherwise overwrite the old file.  Ignored unless
           the 'log' parameter is also provided.";
        type empty;
      }

      leaf log-level {
        description
          "Agent debug logging level to use.";
        type nt:NcDebugType;
          max-access read-write;
          usage optional;
      }

      leaf modpath {
        description
           "Internal file search path for data model modules.";
        type nt:NcPathList;
      }

      leaf runpath {
        description
           "Internal file search path for executable modules.";
        type nt:NcPathList;
      }

      choice start {
        leaf no-startup {
          description
             "If present, do not load the startup config file.";
          type empty;
        }

        leaf startup {
          description
             "The full filespec of the startup config file to use.
              If present, overrides the default startup config
              file name 'startup-cfg.xml',  This will also
              override the NCX_DATAPATH environement variable
              and the datapath CLI parameter, if the first
              character is the forward slash '/', indicating
              an absolute file path.";
          type string;
        }
      }

      leaf version {
        description
	  "Print netconfd version string and exit";
        type empty;
      }
    }

    rpc load-config {
      description "NCX internal load-config operation.";
      ncx:rpc-type config;
      input {
        leaf config {
          description "XML Config contents.";
          type nc:ConfigInlineType;
        }
      }
    }

}
