// Code generated by protoc-gen-yang. DO NOT EDIT.


/* ****************************************************************************************************
 * Import Path : "github.com/Intrising/intri-type/core/lldp"                                          *
 * Dir Path    : github.com/Intrising/intri-type/core/lldp                                            *
 * Go Package  : lldp                                                                                 *
 * Files       : 3                                                                                    *
 **************************************************************************************************** */
module intri-lldp {

  namespace "intri:intri-lldp";

  prefix "intri-lldp";

  organization "Intrising Inc.";

  contact "intrising@intrising.com.tw";

  revision 2022-06-23 {
    description "Build date.";
  }

  import intri-device {
    prefix intri-device;
  }
  import intri-empty {
    prefix intri-empty;
  }


  /* **************************************************************************************************
   * Enums       : 17                                                                                 *
   ************************************************************************************************** */
  /* core/lldp/common.proto */
  typedef PortModeTypeOptions {
    type enumeration {
      enum PORT_MODE_TYPE_DISABLED {
        description "[Disabled] Set port disabled";
        value 0;
      }
      enum PORT_MODE_TYPE_ENABLED_TX_ONLY {
        description "[TX only] Set port only transmit the packet";
        value 1;
      }
      enum PORT_MODE_TYPE_ENABLED_RX_ONLY {
        description "[RX only] Set port only receive the packet";
        value 2;
      }
      enum PORT_MODE_TYPE_ENABLED_TX_RX {
        description "[Both] Set port to receive and transmit the packet";
        value 3;
      }
    }
  }
  /* core/lldp/common.proto */
  typedef CfgAdvertizedMedClassTypeOptions {
    type enumeration {
      enum CFG_ADVERTIZED_MED_CLASS_TYPE_DISABLE_MED {
        description "[Disable MED]";
        value 0;
      }
      enum CFG_ADVERTIZED_MED_CLASS_TYPE_GENERIC_ENDPOINT {
        description "[Generic End Point]";
        value 1;
      }
      enum CFG_ADVERTIZED_MED_CLASS_TYPE_MEDIA_ENDPOINT {
        description "[Media END Point]";
        value 2;
      }
      enum CFG_ADVERTIZED_MED_CLASS_TYPE_COMMUNICATION_ENDPOINT {
        description "[Communication End Point]";
        value 3;
      }
      enum CFG_ADVERTIZED_MED_CLASS_TYPE_NETWORK_DEVICE {
        description "[Network Connectivity Device]";
        value 4;
      }
    }
  }
  /* core/lldp/common.proto */
  typedef MACPHYAdvertisedCapabilityTypeOptions {
    type enumeration {
      enum MAC_PHY_ADVERTIZED_CAPABILITY_TYPE_BASE1000_T_FULL {
        description "[Base 1000T Full]";
        value 0;
      }
      enum MAC_PHY_ADVERTIZED_CAPABILITY_TYPE_BASE1000_T_HALF {
        description "[Base 1000T Half]";
        value 1;
      }
      enum MAC_PHY_ADVERTIZED_CAPABILITY_TYPE_BASE1000_X_FULL {
        description "[Base 1000X Full]";
        value 2;
      }
      enum MAC_PHY_ADVERTIZED_CAPABILITY_TYPE_BASE1000_X_HALF {
        description "[Base 1000X Half]";
        value 3;
      }
      enum MAC_PHY_ADVERTIZED_CAPABILITY_TYPE_ASYM_SYM_PAUSE {
        description "[ASYM SYM Pause]";
        value 4;
      }
      enum MAC_PHY_ADVERTIZED_CAPABILITY_TYPE_SYM_PAUSE {
        description "[SYM Pause]";
        value 5;
      }
      enum MAC_PHY_ADVERTIZED_CAPABILITY_TYPE_ASYM_PAUSE {
        description "[ASYM Pause]";
        value 6;
      }
      enum MAC_PHY_ADVERTIZED_CAPABILITY_TYPE_PAUSE {
        description "[Pause]";
        value 7;
      }
      enum MAC_PHY_ADVERTIZED_CAPABILITY_TYPE_BASE100_T2_FULL {
        description "[Base 100T2 Full]";
        value 8;
      }
      enum MAC_PHY_ADVERTIZED_CAPABILITY_TYPE_BASE100_T2_HALF {
        description "[Base 100T2 Half]";
        value 9;
      }
      enum MAC_PHY_ADVERTIZED_CAPABILITY_TYPE_BASE100_TX_FULL {
        description "[Base 100TX Full]";
        value 10;
      }
      enum MAC_PHY_ADVERTIZED_CAPABILITY_TYPE_BASE100_TX_HALF {
        description "[Base 100TX Half]";
        value 11;
      }
      enum MAC_PHY_ADVERTIZED_CAPABILITY_TYPE_BASE100_T4 {
        description "[Base 100T4]";
        value 12;
      }
      enum MAC_PHY_ADVERTIZED_CAPABILITY_TYPE_BASE10_T_FULL {
        description "[Base 10T Full]";
        value 13;
      }
      enum MAC_PHY_ADVERTIZED_CAPABILITY_TYPE_BASE10_T_HALF {
        description "[Base 10T Half]";
        value 14;
      }
      enum MAC_PHY_ADVERTIZED_CAPABILITY_TYPE_OTHER_OR_UNKNOWN {
        description "[Other or unknown]";
        value 15;
      }
    }
  }
  /* core/lldp/common.proto */
  typedef MedCapabilitiesTypeOptions {
    type enumeration {
      enum MED_CAPABILITIES_TYPE_CAPABILITY {
        description "[Capability]";
        value 0;
      }
      enum MED_CAPABILITIES_TYPE_POLICY {
        description "[Policy]";
        value 1;
      }
      enum MED_CAPABILITIES_TYPE_LOCATION {
        description "[Location]";
        value 2;
      }
      enum MED_CAPABILITIES_TYPE_MDI_PSE {
        description "[MDI PSE]";
        value 3;
      }
      enum MED_CAPABILITIES_TYPE_MDI_PD {
        description "[MDI PD]";
        value 4;
      }
      enum MED_CAPABILITIES_TYPE_INVENTORY {
        description "[Inventory]";
        value 5;
      }
    }
  }
  /* core/lldp/common.proto */
  typedef AltitudeTypeOptions {
    type enumeration {
      enum ALTITUDE_TYPE_METER {
        description "[Meter]";
        value 0;
      }
      enum ALTITUDE_TYPE_FLOOR {
        description "[Floor]";
        value 1;
      }
    }
  }
  /* core/lldp/common.proto */
  typedef ChassisIdSubtypeTypeOptions {
    type enumeration {
      enum CHASSIS_ID_SUBTYPE_TYPE_RESERVED {
        description "[Reserved]";
        value 0;
      }
      enum CHASSIS_ID_SUBTYPE_TYPE_CHASSIS_COMPONENT {
        description "[Chassis Component]";
        value 1;
      }
      enum CHASSIS_ID_SUBTYPE_TYPE_INTERFACE_ALIAS {
        description "[Interface Alias]";
        value 2;
      }
      enum CHASSIS_ID_SUBTYPE_TYPE_PORT_COMPONENT {
        description "[Port Componenet]";
        value 3;
      }
      enum CHASSIS_ID_SUBTYPE_TYPE_MAC_ADDRESS {
        description "[MAC Address]";
        value 4;
      }
      enum CHASSIS_ID_SUBTYPE_TYPE_NETWORK_ADDRESS {
        description "[Network Address]";
        value 5;
      }
      enum CHASSIS_ID_SUBTYPE_TYPE_INTERFACE_NAME {
        description "[Interface Name]";
        value 6;
      }
      enum CHASSIS_ID_SUBTYPE_TYPE_LOCAL {
        description "[Local]";
        value 7;
      }
    }
  }
  /* core/lldp/common.proto */
  typedef CapabilitiesTypeOptions {
    type enumeration {
      enum CAPABILITIES_TYPE_OTHER {
        description "[Other]";
        value 0;
      }
      enum CAPABILITIES_TYPE_REPEATER {
        description "[Repeater]";
        value 1;
      }
      enum CAPABILITIES_TYPE_BRIDGE {
        description "[Bridge]";
        value 2;
      }
      enum CAPABILITIES_TYPE_WLAN {
        description "[WLAN]";
        value 3;
      }
      enum CAPABILITIES_TYPE_ROUTER {
        description "[Router]";
        value 4;
      }
      enum CAPABILITIES_TYPE_TELEPHONE {
        description "[Telephone]";
        value 5;
      }
      enum CAPABILITIES_TYPE_DOCSIS {
        description "[DOCSIS]";
        value 6;
      }
      enum CAPABILITIES_TYPE_STATION {
        description "[Station]";
        value 7;
      }
    }
  }
  /* core/lldp/common.proto */
  typedef ManagementAddressIfSubTypeTypeOptions {
    type enumeration {
      enum MANAGEMENT_ADDRESS_IF_SUBTYPE_TYPE_DONT_USE {
        description "*[dont use]";
        value 0;
      }
      enum MANAGEMENT_ADDRESS_IF_SUBTYPE_TYPE_UNKNOWN {
        description "[Unknown]";
        value 1;
      }
      enum MANAGEMENT_ADDRESS_IF_SUBTYPE_TYPE_IF_INDEX {
        description "[IfIndex]";
        value 2;
      }
      enum MANAGEMENT_ADDRESS_IF_SUBTYPE_TYPE_SYSTEM_PORT_NUMBER {
        description "[System Port number]";
        value 3;
      }
    }
  }
  /* core/lldp/common.proto */
  typedef PortIdSubtypeTypeOptions {
    type enumeration {
      enum PORT_ID_SUBTYPE_TYPE_UNKNOWN {
        description "[Unknown]";
        value 0;
      }
      enum PORT_ID_SUBTYPE_TYPE_INTERFACE_ALIAS {
        description "[Interface Alias]";
        value 1;
      }
      enum PORT_ID_SUBTYPE_TYPE_PORT_COMPONENT {
        description "[Port Component]";
        value 2;
      }
      enum PORT_ID_SUBTYPE_TYPE_MAC_ADDRESS {
        description "[MAC Address]";
        value 3;
      }
      enum PORT_ID_SUBTYPE_TYPE_NETWORK_ADDRESS {
        description "[Network Address]";
        value 4;
      }
      enum PORT_ID_SUBTYPE_TYPE_INTERFACE_NAME {
        description "[Interface Name]";
        value 5;
      }
      enum PORT_ID_SUBTYPE_TYPE_AGENT_CIRCUIT_ID {
        description "[Agent Circuit ID]";
        value 6;
      }
      enum PORT_ID_SUBTYPE_TYPE_LOCAL {
        description "[Local]";
        value 7;
      }
    }
  }
  /* core/lldp/common.proto */
  typedef PoliciesApplicationTypeOptions {
    type enumeration {
      enum POLICIES_APPLICATION_TYPE_UNKNOWN {
        description "[Unknown] Unspecified application";
        value 0;
      }
      enum POLICIES_APPLICATION_TYPE_VOICE {
        description "[Voice] Used by dedicated IP phone handsets and other similar devices supporting interactive voice services";
        value 1;
      }
      enum POLICIES_APPLICATION_TYPE_VOICE_SIGNALING {
        description "[Voice Signaling] Defines a separate policy for the command and control signaling that supports voice applications";
        value 2;
      }
      enum POLICIES_APPLICATION_TYPE_GUEST_VOICE {
        description "[Guest Voice] Limited feature-set voice service for guest users";
        value 3;
      }
      enum POLICIES_APPLICATION_TYPE_GUEST_VOICE_SIGNALING {
        description "[Guest Voice Signaling] Defines a separate policy for the command and control signaling that supports guest voice applications";
        value 4;
      }
      enum POLICIES_APPLICATION_TYPE_SOFTPHONE_VOICE {
        description "[Soft Phone Voice] Used by softphone applications that operate on devices, such as PCs or laptop computers";
        value 5;
      }
      enum POLICIES_APPLICATION_TYPE_VIDEO_CONFERENCING {
        description "[Video Conerencing] Used by video conferencing applications";
        value 6;
      }
      enum POLICIES_APPLICATION_TYPE_STREAMING_VIDEO {
        description "[Streaming Video] Used for streaming video applications";
        value 7;
      }
      enum POLICIES_APPLICATION_TYPE_VIDEO_SIGNALING {
        description "[Video Signaling] Defines a separate policy for the command and control of video applications";
        value 8;
      }
    }
  }
  /* core/lldp/common.proto */
  typedef PoliciesLayer2PriorityTypeOptions {
    type enumeration {
      enum POLICIES_LAYER2_PRIORITY_TYPE_BEST_EFFORT {
        description "[Best Effort]";
        value 0;
      }
      enum POLICIES_LAYER2_PRIORITY_TYPE_UNKNOWN {
        description "[Unknown]";
        value 1;
      }
      enum POLICIES_LAYER2_PRIORITY_TYPE_BACKGROUND {
        description "[Background]";
        value 2;
      }
      enum POLICIES_LAYER2_PRIORITY_TYPE_SPARE {
        description "[Spare]";
        value 3;
      }
      enum POLICIES_LAYER2_PRIORITY_TYPE_EXCELLENT_EFFORT {
        description "[Excellent Effort]";
        value 4;
      }
      enum POLICIES_LAYER2_PRIORITY_TYPE_CONTROLLED_LOAD {
        description "[Controlled Load]";
        value 5;
      }
      enum POLICIES_LAYER2_PRIORITY_TYPE_VIDEO {
        description "[Video]";
        value 6;
      }
      enum POLICIES_LAYER2_PRIORITY_TYPE_VOICE {
        description "[Voice]";
        value 7;
      }
      enum POLICIES_LAYER2_PRIORITY_TYPE_NETWORK_CONTROL {
        description "[Network Control]";
        value 8;
      }
    }
  }
  /* core/lldp/common.proto */
  typedef PoePortClassTypeOptions {
    type enumeration {
      enum POE_PORT_CLASS_TYPE_PD {
        description "[PD]";
        value 0;
      }
      enum POE_PORT_CLASS_TYPE_PSE {
        description "[PSE]";
        value 1;
      }
    }
  }
  /* core/lldp/common.proto */
  typedef PoeInfoTypeOptions {
    type enumeration {
      enum POE_INFO_TYPE_2_PSE_DEVICE {
        description "[Type2 PSE]";
        value 0;
      }
      enum POE_INFO_TYPE_2_PD_DEVICE {
        description "[Type2 PD]";
        value 1;
      }
      enum POE_INFO_TYPE_1_PSE_DEVICE {
        description "[Type1 PSE]";
        value 2;
      }
      enum POE_INFO_TYPE_1_PD_DEVICE {
        description "[Type1 PD]";
        value 3;
      }
    }
  }
  /* core/lldp/common.proto */
  typedef PoeInfoSourceTypeOptions {
    type enumeration {
      enum POE_INFO_SOURCE_TYPE_UNKNOWN {
        description "[Unknown] No information received";
        value 0;
      }
      enum POE_INFO_SOURCE_TYPE_PD_PSE_PRIMARY {
        description "[PD PSE Primary] For type PD: Power source is the PSE. For type PSE: Power source is the primary power source";
        value 1;
      }
      enum POE_INFO_SOURCE_TYPE_PD_LOCAL_BACKUP {
        description "[PD Local Backup] For type PD: Power source is a local source. For type PSE: Power source is the backup power source";
        value 2;
      }
      enum POE_INFO_SOURCE_TYPE_PD_PSE_LOCAL {
        description "[PD PSE Local] For type PD: The power source is both the PSE and a local source. For type PSE: this value should not occur";
        value 3;
      }
    }
  }
  /* core/lldp/common.proto */
  typedef PoeInfoPriorityTypeOptions {
    type enumeration {
      enum POE_INFO_PRIORITY_TYPE_UNKNOWN {
        description "[Unknown] No information received";
        value 0;
      }
      enum POE_INFO_PRIORITY_TYPE_CRITICAL {
        description "[Critical] Critical priority";
        value 1;
      }
      enum POE_INFO_PRIORITY_TYPE_HIGH {
        description "[High] High priority";
        value 2;
      }
      enum POE_INFO_PRIORITY_TYPE_LOW {
        description "[Low] Low priority";
        value 3;
      }
    }
  }
  /* core/lldp/common.proto */
  typedef PoeControlPowerPairsTypeOptions {
    type enumeration {
      enum POE_CONTROL_POWER_PAIRS_TYPE_SIGNAL {
        description "[Signal]";
        value 0;
      }
      enum POE_CONTROL_POWER_PAIRS_TYPE_SPARE {
        description "[Spare]";
        value 1;
      }
    }
  }
  /* core/lldp/common.proto */
  typedef PoeControlPowerClassTypeOptions {
    type enumeration {
      enum POE_CONTROL_POWER_CLASS_TYPE_NONE {
        description "[None]";
        value 0;
      }
      enum POE_CONTROL_POWER_CLASS_TYPE_0 {
        description "[Type0]";
        value 1;
      }
      enum POE_CONTROL_POWER_CLASS_TYPE_1 {
        description "[Type1]";
        value 2;
      }
      enum POE_CONTROL_POWER_CLASS_TYPE_2 {
        description "[Type2]";
        value 3;
      }
      enum POE_CONTROL_POWER_CLASS_TYPE_3 {
        description "[Type3]";
        value 4;
      }
      enum POE_CONTROL_POWER_CLASS_TYPE_4 {
        description "[Type4]";
        value 5;
      }
      enum POE_CONTROL_POWER_CLASS_TYPE_5 {
        description "[Type5]";
        value 6;
      }
      enum POE_CONTROL_POWER_CLASS_TYPE_6 {
        description "[Type6]";
        value 7;
      }
      enum POE_CONTROL_POWER_CLASS_TYPE_7 {
        description "[Type7]";
        value 8;
      }
      enum POE_CONTROL_POWER_CLASS_TYPE_8 {
        description "[Type8]";
        value 9;
      }
    }
  }


  /* **************************************************************************************************
   * Msgs        : 22                                                                                 *
   ************************************************************************************************** */
  /* core/lldp/lldp.proto */
  grouping Config {
    container SystemConfig {
      uses SystemConfig;
    }
    container PortConfig {
      uses PortConfig;
    }
  }
  /* core/lldp/lldp.proto */
  grouping SystemConfig {
    leaf Enabled {
      type boolean;
    }
    leaf TimeToLive {
      type int32;
    }
    leaf MsgTxInterval {
      type int32;
    }
    leaf VoiceDisableVlanTLV {
      type boolean;
    }
    leaf ForwardToLink {
      type boolean;
    }
  }
  /* core/lldp/lldp.proto */
  grouping PortConfig {
    container List {
      list List_Entry {
        uses PortConfigEntry;
      }
    }
  }
  /* core/lldp/lldp.proto */
  grouping PortConfigEntry {
    container IdentifyNo {
      uses intri-device:InterfaceIdentify;
    }
    leaf Mode {
      type PortModeTypeOptions;
    }
  }
  /* core/lldp/lldp.proto */
  grouping LocalInfo {
    container List {
      list List_Entry {
        uses LocalInfoEntry;
      }
    }
  }
  /* core/lldp/lldp.proto */
  grouping NeighborInfo {
    container List {
      list List_Entry {
        uses NeighborInfoEntry;
      }
    }
  }
  /* core/lldp/lldp.proto */
  grouping LocalInfoEntry {
    container IdentifyNo {
      uses intri-device:InterfaceIdentify;
    }
    container MACPhy {
      uses MACPHYConfig;
    }
    container PortMgmt {
      uses PortManagementInfo;
    }
    container Aggr {
      uses LinkAggregation;
    }
    container ExtendPoe {
      uses ExtendedPowerViaMDI;
    }
    container Power {
      uses PowerViaMDI;
    }
    container MediaCap {
      uses MediaCapability;
    }
    container SystemInfo {
      uses SystemManagementInfo;
    }
  }
  /* core/lldp/lldp.proto */
  grouping NeighborInfoEntry {
    container RecvIdentifyNo {
      uses intri-device:InterfaceIdentify;
    }
    leaf TimeToLive {
      type int32;
    }
    container Chassis {
      uses ChassisInfo;
    }
    container MgmtAddress {
      list MgmtAddress_Entry {
        uses PortManagementAddressInfo;
      }
    }
    container Capabilities {
      leaf-list Capabilities_Entry {
        type CapabilitiesTypeOptions;
      }
    }
    container CapabilitiesEnabled {
      leaf-list CapabilitiesEnabled_Entry {
        type CapabilitiesTypeOptions;
      }
    }
    container MedCapabilities {
      leaf-list MedCapabilities_Entry {
        type MedCapabilitiesTypeOptions;
      }
    }
    container PortSubtype {
      uses PortID;
    }
    container VoiceVlan {
      list VoiceVlan_Entry {
        uses VoiceVlanEntry;
      }
    }
    container SystemInfo {
      uses SystemManagementInfo;
    }
    container ExtendPoe {
      uses ExtendedPowerViaMDI;
    }
    container Power {
      uses PowerViaMDI;
    }
  }
  /* core/lldp/lldp.proto */
  grouping LinkAggregation {
    leaf Capabilities {
      type boolean;
    }
    leaf Status {
      type boolean;
    }
    leaf AggregationPortNo {
      type int32;
    }
  }
  /* core/lldp/lldp.proto */
  grouping ExtendedPowerViaMDI {
    leaf Type {
      type PoeInfoTypeOptions;
    }
    leaf Source {
      type PoeInfoSourceTypeOptions;
    }
    leaf Priority {
      type PoeInfoPriorityTypeOptions;
    }
    leaf Value {
      type decimal64 {
        fraction-digits 2;
      }
    }
  }
  /* core/lldp/lldp.proto */
  grouping MACPHYConfig {
    leaf AutoNegotiationConfig {
      type boolean;
    }
    leaf AutoNegotiationStatus {
      type boolean;
    }
    container AutoNegoAdvertisedCapability {
      leaf-list AutoNegoAdvertisedCapability_Entry {
        type MACPHYAdvertisedCapabilityTypeOptions;
      }
    }
    leaf OperationalMAUType {
      type MACPHYAdvertisedCapabilityTypeOptions;
    }
  }
  /* core/lldp/lldp.proto */
  grouping MediaCapability {
    container Capabilities {
      leaf-list Capabilities_Entry {
        type MedCapabilitiesTypeOptions;
      }
    }
    leaf ClassType {
      type int32;
    }
  }
  /* core/lldp/lldp.proto */
  grouping SystemManagementInfo {
    leaf Name {
      type string;
    }
    leaf Description {
      type string;
    }
  }
  /* core/lldp/lldp.proto */
  grouping PortManagementInfo {
    container Ip {
      leaf-list Ip_Entry {
        type string;
      }
    }
    leaf MACAddr {
      type string;
    }
    leaf Description {
      type string;
    }
  }
  /* core/lldp/lldp.proto */
  grouping PowerViaMDI {
    leaf Type {
      type PoePortClassTypeOptions;
    }
    leaf PoePowerSupported {
      type boolean;
    }
    leaf PoePowerEnabled {
      type boolean;
    }
    leaf PairControl {
      type boolean;
    }
    leaf PowerPairs {
      type PoeControlPowerPairsTypeOptions;
    }
    leaf PowerClass {
      type PoeControlPowerClassTypeOptions;
    }
    leaf DeviceType {
      type PoeInfoTypeOptions;
    }
    leaf Source {
      type PoeInfoSourceTypeOptions;
    }
    leaf Priority {
      type PoeInfoPriorityTypeOptions;
    }
    leaf PdRequestedPower {
      type decimal64 {
        fraction-digits 2;
      }
    }
    leaf PseAllocatedPower {
      type decimal64 {
        fraction-digits 2;
      }
    }
  }
  /* core/lldp/lldp.proto */
  grouping PortManagementAddressInfo {
    leaf Ip {
      type string;
    }
    leaf Subtype {
      type ManagementAddressIfSubTypeTypeOptions;
    }
    leaf ID {
      type string;
    }
  }
  /* core/lldp/lldp.proto */
  grouping ManagementAddress {
    leaf MACAddr {
      type string;
    }
    container Ip {
      leaf-list Ip_Entry {
        type string;
      }
    }
    leaf PortDsr {
      type string;
    }
  }
  /* core/lldp/lldp.proto */
  grouping ChassisInfo {
    leaf Type {
      type ChassisIdSubtypeTypeOptions;
    }
    leaf ID {
      type string;
    }
  }
  /* core/lldp/lldp.proto */
  grouping PortID {
    leaf Subtype {
      type PortIdSubtypeTypeOptions;
    }
    leaf VlanID {
      type int32;
    }
    leaf ID {
      type string;
    }
  }
  /* core/lldp/lldp.proto */
  grouping Statistic {
    container List {
      list List_Entry {
        uses StatisticEntry;
      }
    }
  }
  /* core/lldp/lldp.proto */
  grouping StatisticEntry {
    container IdentifyNo {
      uses intri-device:InterfaceIdentify;
    }
    leaf FramesOut {
      type int32;
    }
    leaf FramesIn {
      type int32;
    }
    leaf FramesInErrors {
      type int32;
    }
  }
  /* core/lldp/lldp.proto */
  grouping VoiceVlanEntry {
    leaf ApplicationType {
      type PoliciesApplicationTypeOptions;
    }
    leaf PolicyDefined {
      type boolean;
    }
    leaf TaggedVlan {
      type boolean;
    }
    leaf VlanID {
      type int32;
    }
    leaf Layer_2Priority {
      type PoliciesLayer2PriorityTypeOptions;
    }
    leaf DSCP {
      type int32;
    }
  }


  /* **************************************************************************************************
   * Services    : 1                                                                                  *
   ************************************************************************************************** */

  /* **************************************************************************************************
   * Service     : LLDP                                                                               *
   * Methods     : 10                                                                                 *
   ************************************************************************************************** */
  /* core/lldp/service.proto */
  rpc intri-lldp-GetConfig {
    output  {
      uses Config;
    }
  }
  /* core/lldp/service.proto */
  rpc intri-lldp-SetConfig {
    input  {
      uses Config;
    }
  }
  /* core/lldp/service.proto */
  rpc intri-lldp-SetSystem {
    input  {
      uses SystemConfig;
    }
  }
  /* core/lldp/service.proto */
  rpc intri-lldp-GetSystem {
    output  {
      uses SystemConfig;
    }
  }
  /* core/lldp/service.proto */
  rpc intri-lldp-SetPortConfig {
    input  {
      uses PortConfig;
    }
  }
  /* core/lldp/service.proto */
  rpc intri-lldp-GetPortConfig {
    output  {
      uses PortConfig;
    }
  }
  /* core/lldp/service.proto */
  rpc intri-lldp-GetLocalInfo {
    output  {
      uses LocalInfo;
    }
  }
  /* core/lldp/service.proto */
  rpc intri-lldp-GetNeighborInfo {
    output  {
      uses NeighborInfo;
    }
  }
  /* core/lldp/service.proto */
  rpc intri-lldp-GetStatistic {
    output  {
      uses Statistic;
    }
  }
  /* core/lldp/service.proto */
  rpc intri-lldp-RunClearStatistic {
    input  {
      uses intri-device:PortList;
    }
  }

}
