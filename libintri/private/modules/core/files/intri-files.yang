module intri-files {
  namespace "intri:intri-files";
  prefix "intri-files";
  import filespb {
    prefix "filespb";
  }
  organization "Intrising Inc.";
  contact "xxx@intrising.com.tw";
  revision 2022-06-14 {
    description "Build date.";
  }
}
