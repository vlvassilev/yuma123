module intri-cdp {
  namespace "intri:intri-cdp";
  prefix "intri-cdp";
  import cdppb {
    prefix "cdppb";
  }
  organization "Intrising Inc.";
  contact "xxx@intrising.com.tw";
  revision 2022-06-14 {
    description "Build date.";
  }
}
