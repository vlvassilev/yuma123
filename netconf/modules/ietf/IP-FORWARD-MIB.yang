/*
 * This module has been generated by smidump 0.4.6:
 *
 *      smidump -f yang --yang-smi-extensions IP-FORWARD-MIB
 *
 * Do not edit. Edit the source file instead!
 */

module IP-FORWARD-MIB {

   /*** NAMESPACE / PREFIX DEFINITION ***/

   namespace "urn:ietf:params:xml:ns:yang:smiv2:IP-FORWARD-MIB";
   prefix "ip-forward";

   /*** LINKAGE (IMPORTS / INCLUDES) ***/

   import IANA-RTPROTO-MIB { prefix "iana-rtproto"; }
   import IF-MIB           { prefix "if-mib"; }
   import INET-ADDRESS-MIB { prefix "inet-address"; }
   import IP-MIB           { prefix "ip-mib"; }
   import SNMPv2-TC        { prefix "smiv2"; }
   import ietf-inet-types  { prefix "inet"; }
   import yang-smi         { prefix "smi"; }
   import ietf-yang-types  { prefix "yang"; }

   /*** META INFORMATION ***/

   organization     
     "IETF IPv6 Working Group
      http://www.ietf.org/html.charters/ipv6-charter.html";

   contact          
     "Editor:
      Brian Haberman
      Johns Hopkins University - Applied Physics Laboratory
      Mailstop 17-S442
      11100 Johns Hopkins Road
      Laurel MD,  20723-6099  USA
      
      Phone: +1-443-778-1319
      Email: brian@innovationslab.net
      
      Send comments to <ipv6@ietf.org>";

   description      
     "The MIB module for the management of CIDR multipath IP
      Routes.
      
      Copyright (C) The Internet Society (2006).  This version
      of this MIB module is a part of RFC 4292; see the RFC
      itself for full legal notices.";

   revision "2006-02-01" {
      description   
        "IPv4/v6 version-independent revision.  Minimal changes
         were made to the original RFC 2096 MIB to allow easy
         upgrade of existing IPv4 implementations to the
         version-independent MIB.  These changes include:
         
         Adding inetCidrRouteDiscards as a replacement for the
         deprecated ipRoutingDiscards and ipv6DiscardedRoutes
         objects.
         
         Adding a new conformance statement to support the
         implementation of the IP Forwarding MIB in a
         read-only mode.
         
         
         
         
         The inetCidrRouteTable replaces the IPv4-specific
         ipCidrRouteTable, its related objects, and related
         conformance statements.
         
         Published as RFC 4292.";
   }
   revision "1996-09-19" {
      description   
        "Revised to support CIDR routes.
         Published as RFC 2096.";
   }
   revision "1992-07-02" {
      description   
        "Initial version, published as RFC 1354.";
   }

   container ipForward {

      leaf ipForwardNumber {
         type yang:gauge32;
         config false;
         status obsolete;
         description 
           "The number of current ipForwardTable entries that are
            not invalid.";
         smi:oid "1.3.6.1.2.1.4.24.1";
      }


      /* XXX table comments here XXX */

      list ipForwardEntry {

         key "ipForwardDest ipForwardProto ipForwardPolicy 
              ipForwardNextHop";
         status obsolete;
         description 
           "A particular route to a particular destination, under a
            particular policy.";
         smi:oid "1.3.6.1.2.1.4.24.2.1";


         leaf ipForwardDest {
            type inet:ipv4-address;
            config false;
            status obsolete;
            description   
              "The destination IP address of this route.  An entry
               with a value of 0.0.0.0 is considered a default route.
               
               This object may not take a Multicast (Class D) address
               value.
               
               Any assignment (implicit or otherwise) of an instance
               of this object to a value x must be rejected if the
               bitwise logical-AND of x with the value of the
               corresponding instance of the ipForwardMask object is
               not equal to x.";
            smi:oid "1.3.6.1.2.1.4.24.2.1.1";
         }

         leaf ipForwardMask {
            type inet:ipv4-address;
            config true;
            status obsolete;
            description   
              "Indicate the mask to be logical-ANDed with the
               destination address before being compared to the value
               in the ipForwardDest field.  For those systems that do
               not support arbitrary subnet masks, an agent constructs
               the value of the ipForwardMask by reference to the IP
               Address Class.
               
               Any assignment (implicit or otherwise) of an instance
               of this object to a value x must be rejected if the
               bitwise logical-AND of x with the value of the
               corresponding instance of the ipForwardDest object is
               not equal to ipForwardDest.";
            smi:default "0x00000000";
            smi:oid "1.3.6.1.2.1.4.24.2.1.2";
         }

         leaf ipForwardPolicy {
            type int32 {
               range "0..2147483647";
            }
            config false;
            status obsolete;
            description   
              "The general set of conditions that would cause
               the selection of one multipath route (set of
               next hops for a given destination) is referred
               to as 'policy'.
               
               Unless the mechanism indicated by ipForwardProto
               specifies otherwise, the policy specifier is
               the IP TOS Field.  The encoding of IP TOS is as
               specified by the following convention.  Zero
               indicates the default path if no more specific
               policy applies.
               
               +-----+-----+-----+-----+-----+-----+-----+-----+
               |                 |                       |     |
               |   PRECEDENCE    |    TYPE OF SERVICE    |  0  |
               |                 |                       |     |
               +-----+-----+-----+-----+-----+-----+-----+-----+
               
               
               
                            IP TOS                IP TOS
                  Field     Policy      Field     Policy
                  Contents    Code      Contents    Code
                  0 0 0 0  ==>   0      0 0 0 1  ==>   2
                  0 0 1 0  ==>   4      0 0 1 1  ==>   6
                  0 1 0 0  ==>   8      0 1 0 1  ==>  10
                  0 1 1 0  ==>  12      0 1 1 1  ==>  14
                  1 0 0 0  ==>  16      1 0 0 1  ==>  18
                  1 0 1 0  ==>  20      1 0 1 1  ==>  22
                  1 1 0 0  ==>  24      1 1 0 1  ==>  26
                  1 1 1 0  ==>  28      1 1 1 1  ==>  30
               
               Protocols defining 'policy' otherwise must either
               define a set of values that are valid for
               this object or must implement an integer-instanced
               policy table for which this object's
               value acts as an index.";
            smi:oid "1.3.6.1.2.1.4.24.2.1.3";
         }

         leaf ipForwardNextHop {
            type inet:ipv4-address;
            config false;
            status obsolete;
            description   
              "On remote routes, the address of the next system en
               route; otherwise, 0.0.0.0.";
            smi:oid "1.3.6.1.2.1.4.24.2.1.4";
         }

         leaf ipForwardIfIndex {
            type int32;
            config true;
            status obsolete;
            description   
              "The ifIndex value that identifies the local interface
               through which the next hop of this route should be
               reached.";
            smi:default "0";
            smi:oid "1.3.6.1.2.1.4.24.2.1.5";
         }

         leaf ipForwardType {
            type enumeration {
               enum other   { value 1; }
               enum invalid { value 2; }
               enum local   { value 3; }
               enum remote  { value 4; }
            }
            config true;
            status obsolete;
            description   
              "The type of route.  Note that local(3) refers to a
               route for which the next hop is the final destination;
               remote(4) refers to a route for which the next hop is
               not the final destination.
               
               Setting this object to the value invalid(2) has the
               effect of invalidating the corresponding entry in the
               ipForwardTable object.  That is, it effectively
               disassociates the destination identified with said
               entry from the route identified with said entry.  It is
               an implementation-specific matter as to whether the
               agent removes an invalidated entry from the table.
               Accordingly, management stations must be prepared to
               receive tabular information from agents that
               corresponds to entries not currently in use.  Proper
               interpretation of such entries requires examination of
               the relevant ipForwardType object.";
            smi:default "invalid";
            smi:oid "1.3.6.1.2.1.4.24.2.1.6";
         }

         leaf ipForwardProto {
            type enumeration {
               enum other     { value 1; }
               enum local     { value 2; }
               enum netmgmt   { value 3; }
               enum icmp      { value 4; }
               enum egp       { value 5; }
               enum ggp       { value 6; }
               enum hello     { value 7; }
               enum rip       { value 8; }
               enum is-is     { value 9; }
               enum es-is     { value 10; }
               enum ciscoIgrp { value 11; }
               enum bbnSpfIgp { value 12; }
               enum ospf      { value 13; }
               enum bgp       { value 14; }
               enum idpr      { value 15; }
            }
            config false;
            status obsolete;
            description   
              "The routing mechanism via which this route was learned.
               Inclusion of values for gateway routing protocols is
               not intended to imply that hosts should support those
               protocols.";
            smi:oid "1.3.6.1.2.1.4.24.2.1.7";
         }

         leaf ipForwardAge {
            type int32;
            config false;
            status obsolete;
            description   
              "The number of seconds since this route was last updated
               or otherwise determined to be correct.  Note that no
               semantics of `too old' can be implied except through
               knowledge of the routing protocol by which the route
               was learned.";
            smi:default "0";
            smi:oid "1.3.6.1.2.1.4.24.2.1.8";
         }

         leaf ipForwardInfo {
            type yang:object-identifier;
            config true;
            status obsolete;
            description   
              "A reference to MIB definitions specific to the
               particular routing protocol that is responsible for
               this route, as determined by the value specified in the
               route's ipForwardProto value.  If this information is
               not present, its value should be set to the OBJECT
               IDENTIFIER { 0 0 }, which is a syntactically valid
               object identifier, and any implementation conforming to
               ASN.1 and the Basic Encoding Rules must be able to
               generate and recognize this value.";
            smi:oid "1.3.6.1.2.1.4.24.2.1.9";
         }

         leaf ipForwardNextHopAS {
            type int32;
            config true;
            status obsolete;
            description   
              "The Autonomous System Number of the Next Hop.  When
               this is unknown or not relevant to the protocol
               indicated by ipForwardProto, zero.";
            smi:default "0";
            smi:oid "1.3.6.1.2.1.4.24.2.1.10";
         }

         leaf ipForwardMetric1 {
            type int32;
            config true;
            status obsolete;
            description   
              "The primary routing metric for this route.  The
               semantics of this metric are determined by the routing-
               protocol specified in the route's ipForwardProto value.
               If this metric is not used, its value should be set to
               -1.";
            smi:default "-1";
            smi:oid "1.3.6.1.2.1.4.24.2.1.11";
         }

         leaf ipForwardMetric2 {
            type int32;
            config true;
            status obsolete;
            description   
              "An alternate routing metric for this route.  The
               semantics of this metric are determined by the routing-
               protocol specified in the route's ipForwardProto value.
               If this metric is not used, its value should be set to
               -1.";
            smi:default "-1";
            smi:oid "1.3.6.1.2.1.4.24.2.1.12";
         }

         leaf ipForwardMetric3 {
            type int32;
            config true;
            status obsolete;
            description   
              "An alternate routing metric for this route.  The
               semantics of this metric are determined by the routing-
               protocol specified in the route's ipForwardProto value.
               If this metric is not used, its value should be set to
               -1.";
            smi:default "-1";
            smi:oid "1.3.6.1.2.1.4.24.2.1.13";
         }

         leaf ipForwardMetric4 {
            type int32;
            config true;
            status obsolete;
            description   
              "An alternate routing metric for this route.  The
               semantics of this metric are determined by the routing-
               protocol specified in the route's ipForwardProto value.
               If this metric is not used, its value should be set to
               -1.";
            smi:default "-1";
            smi:oid "1.3.6.1.2.1.4.24.2.1.14";
         }

         leaf ipForwardMetric5 {
            type int32;
            config true;
            status obsolete;
            description   
              "An alternate routing metric for this route.  The
               semantics of this metric are determined by the routing-
               protocol specified in the route's ipForwardProto value.
               If this metric is not used, its value should be set to
               -1.";
            smi:default "-1";
            smi:oid "1.3.6.1.2.1.4.24.2.1.15";
         }
      }

      leaf ipCidrRouteNumber {
         type yang:gauge32;
         config false;
         status deprecated;
         description 
           "The number of current ipCidrRouteTable entries that are
            not invalid.  This object is deprecated in favor of
            inetCidrRouteNumber and the inetCidrRouteTable.";
         smi:oid "1.3.6.1.2.1.4.24.3";
      }


      /* XXX table comments here XXX */

      list ipCidrRouteEntry {

         key "ipCidrRouteDest ipCidrRouteMask ipCidrRouteTos 
              ipCidrRouteNextHop";
         status deprecated;
         description 
           "A particular route to a particular destination, under a
            
            
            
            particular policy.";
         smi:oid "1.3.6.1.2.1.4.24.4.1";


         leaf ipCidrRouteDest {
            type inet:ipv4-address;
            config false;
            status deprecated;
            description   
              "The destination IP address of this route.
               
               This object may not take a Multicast (Class D) address
               value.
               
               Any assignment (implicit or otherwise) of an instance
               of this object to a value x must be rejected if the
               bitwise logical-AND of x with the value of the
               corresponding instance of the ipCidrRouteMask object is
               not equal to x.";
            smi:oid "1.3.6.1.2.1.4.24.4.1.1";
         }

         leaf ipCidrRouteMask {
            type inet:ipv4-address;
            config false;
            status deprecated;
            description   
              "Indicate the mask to be logical-ANDed with the
               destination address before being compared to the value
               in the ipCidrRouteDest field.  For those systems that
               do not support arbitrary subnet masks, an agent
               constructs the value of the ipCidrRouteMask by
               reference to the IP Address Class.
               
               Any assignment (implicit or otherwise) of an instance
               of this object to a value x must be rejected if the
               bitwise logical-AND of x with the value of the
               corresponding instance of the ipCidrRouteDest object is
               not equal to ipCidrRouteDest.";
            smi:oid "1.3.6.1.2.1.4.24.4.1.2";
         }

         leaf ipCidrRouteTos {
            type int32 {
               range "0..2147483647";
            }
            config false;
            status deprecated;
            description   
              "The policy specifier is the IP TOS Field.  The encoding
               of IP TOS is as specified by the following convention.
               Zero indicates the default path if no more specific
               policy applies.
               
               +-----+-----+-----+-----+-----+-----+-----+-----+
               |                 |                       |     |
               |   PRECEDENCE    |    TYPE OF SERVICE    |  0  |
               |                 |                       |     |
               +-----+-----+-----+-----+-----+-----+-----+-----+
               
                            IP TOS                IP TOS
                  Field     Policy      Field     Policy
                  Contents    Code      Contents    Code
                  0 0 0 0  ==>   0      0 0 0 1  ==>   2
                  0 0 1 0  ==>   4      0 0 1 1  ==>   6
                  0 1 0 0  ==>   8      0 1 0 1  ==>  10
                  0 1 1 0  ==>  12      0 1 1 1  ==>  14
                  1 0 0 0  ==>  16      1 0 0 1  ==>  18
                  1 0 1 0  ==>  20      1 0 1 1  ==>  22
               
               
               
                  1 1 0 0  ==>  24      1 1 0 1  ==>  26
                  1 1 1 0  ==>  28      1 1 1 1  ==>  30";
            smi:oid "1.3.6.1.2.1.4.24.4.1.3";
         }

         leaf ipCidrRouteNextHop {
            type inet:ipv4-address;
            config false;
            status deprecated;
            description   
              "On remote routes, the address of the next system en
               route; Otherwise, 0.0.0.0.";
            smi:oid "1.3.6.1.2.1.4.24.4.1.4";
         }

         leaf ipCidrRouteIfIndex {
            type int32;
            config true;
            status deprecated;
            description   
              "The ifIndex value that identifies the local interface
               through which the next hop of this route should be
               reached.";
            smi:default "0";
            smi:oid "1.3.6.1.2.1.4.24.4.1.5";
         }

         leaf ipCidrRouteType {
            type enumeration {
               enum other  { value 1; }
               enum reject { value 2; }
               enum local  { value 3; }
               enum remote { value 4; }
            }
            config true;
            status deprecated;
            description   
              "The type of route.  Note that local(3) refers to a
               route for which the next hop is the final destination;
               remote(4) refers to a route for which the next hop is
               not the final destination.
               
               Routes that do not result in traffic forwarding or
               rejection should not be displayed, even if the
               implementation keeps them stored internally.
               
               reject (2) refers to a route that, if matched,
               discards the message as unreachable.  This is used in
               some protocols as a means of correctly aggregating
               routes.";
            smi:oid "1.3.6.1.2.1.4.24.4.1.6";
         }

         leaf ipCidrRouteProto {
            type enumeration {
               enum other      { value 1; }
               enum local      { value 2; }
               enum netmgmt    { value 3; }
               enum icmp       { value 4; }
               enum egp        { value 5; }
               enum ggp        { value 6; }
               enum hello      { value 7; }
               enum rip        { value 8; }
               enum isIs       { value 9; }
               enum esIs       { value 10; }
               enum ciscoIgrp  { value 11; }
               enum bbnSpfIgp  { value 12; }
               enum ospf       { value 13; }
               enum bgp        { value 14; }
               enum idpr       { value 15; }
               enum ciscoEigrp { value 16; }
            }
            config false;
            status deprecated;
            description   
              "The routing mechanism via which this route was learned.
               Inclusion of values for gateway routing protocols is
               not intended to imply that hosts should support those
               protocols.";
            smi:oid "1.3.6.1.2.1.4.24.4.1.7";
         }

         leaf ipCidrRouteAge {
            type int32;
            config false;
            status deprecated;
            description   
              "The number of seconds since this route was last updated
               or otherwise determined to be correct.  Note that no
               semantics of `too old' can be implied, except through
               knowledge of the routing protocol by which the route
               was learned.";
            smi:default "0";
            smi:oid "1.3.6.1.2.1.4.24.4.1.8";
         }

         leaf ipCidrRouteInfo {
            type yang:object-identifier;
            config true;
            status deprecated;
            description   
              "A reference to MIB definitions specific to the
               particular routing protocol that is responsible for
               this route, as determined by the value specified in the
               route's ipCidrRouteProto value.  If this information is
               not present, its value should be set to the OBJECT
               IDENTIFIER { 0 0 }, which is a syntactically valid
               object identifier, and any implementation conforming to
               ASN.1 and the Basic Encoding Rules must be able to
               generate and recognize this value.";
            smi:oid "1.3.6.1.2.1.4.24.4.1.9";
         }

         leaf ipCidrRouteNextHopAS {
            type int32;
            config true;
            status deprecated;
            description   
              "The Autonomous System Number of the Next Hop.  The
               semantics of this object are determined by the routing-
               protocol specified in the route's ipCidrRouteProto
               value.  When this object is unknown or not relevant, its
               value should be set to zero.";
            smi:default "0";
            smi:oid "1.3.6.1.2.1.4.24.4.1.10";
         }

         leaf ipCidrRouteMetric1 {
            type int32;
            config true;
            status deprecated;
            description   
              "The primary routing metric for this route.  The
               semantics of this metric are determined by the routing-
               protocol specified in the route's ipCidrRouteProto
               value.  If this metric is not used, its value should be
               set to -1.";
            smi:default "-1";
            smi:oid "1.3.6.1.2.1.4.24.4.1.11";
         }

         leaf ipCidrRouteMetric2 {
            type int32;
            config true;
            status deprecated;
            description   
              "An alternate routing metric for this route.  The
               semantics of this metric are determined by the routing-
               protocol specified in the route's ipCidrRouteProto
               value.  If this metric is not used, its value should be
               
               
               
               set to -1.";
            smi:default "-1";
            smi:oid "1.3.6.1.2.1.4.24.4.1.12";
         }

         leaf ipCidrRouteMetric3 {
            type int32;
            config true;
            status deprecated;
            description   
              "An alternate routing metric for this route.  The
               semantics of this metric are determined by the routing-
               protocol specified in the route's ipCidrRouteProto
               value.  If this metric is not used, its value should be
               set to -1.";
            smi:default "-1";
            smi:oid "1.3.6.1.2.1.4.24.4.1.13";
         }

         leaf ipCidrRouteMetric4 {
            type int32;
            config true;
            status deprecated;
            description   
              "An alternate routing metric for this route.  The
               semantics of this metric are determined by the routing-
               protocol specified in the route's ipCidrRouteProto
               value.  If this metric is not used, its value should be
               set to -1.";
            smi:default "-1";
            smi:oid "1.3.6.1.2.1.4.24.4.1.14";
         }

         leaf ipCidrRouteMetric5 {
            type int32;
            config true;
            status deprecated;
            description   
              "An alternate routing metric for this route.  The
               semantics of this metric are determined by the routing-
               protocol specified in the route's ipCidrRouteProto
               value.  If this metric is not used, its value should be
               set to -1.";
            smi:default "-1";
            smi:oid "1.3.6.1.2.1.4.24.4.1.15";
         }

         leaf ipCidrRouteStatus {
            type smiv2:RowStatus;
            config true;
            status deprecated;
            description   
              "The row status variable, used according to row
               installation and removal conventions.";
            smi:oid "1.3.6.1.2.1.4.24.4.1.16";
         }
      }


      leaf inetCidrRouteNumber {
         type yang:gauge32;
         config false;
         description 
           "The number of current inetCidrRouteTable entries that
            are not invalid.";
         smi:oid "1.3.6.1.2.1.4.24.6";
      }


      /* XXX table comments here XXX */

      list inetCidrRouteEntry {

         key "inetCidrRouteDestType inetCidrRouteDest 
              inetCidrRoutePfxLen inetCidrRoutePolicy 
              inetCidrRouteNextHopType inetCidrRouteNextHop";
         description 
           "A particular route to a particular destination, under a
            particular policy (as reflected in the
            inetCidrRoutePolicy object).
            
            Dynamically created rows will survive an agent reboot.
            
            Implementers need to be aware that if the total number
            of elements (octets or sub-identifiers) in
            inetCidrRouteDest, inetCidrRoutePolicy, and
            inetCidrRouteNextHop exceeds 111, then OIDs of column
            instances in this table will have more than 128 sub-
            identifiers and cannot be accessed using SNMPv1,
            SNMPv2c, or SNMPv3.";
         smi:oid "1.3.6.1.2.1.4.24.7.1";


         leaf inetCidrRouteDestType {
            type inet-address:InetAddressType;
            config false;
            description   
              "The type of the inetCidrRouteDest address, as defined
               in the InetAddress MIB.
               
               Only those address types that may appear in an actual
               routing table are allowed as values of this object.";
            reference 
              "RFC 4001";
            smi:oid "1.3.6.1.2.1.4.24.7.1.1";
         }

         leaf inetCidrRouteDest {
            type inet-address:InetAddress;
            config false;
            description   
              "The destination IP address of this route.
               
               The type of this address is determined by the value of
               the inetCidrRouteDestType object.
               
               The values for the index objects inetCidrRouteDest and
               inetCidrRoutePfxLen must be consistent.  When the value
               of inetCidrRouteDest (excluding the zone index, if one
               is present) is x, then the bitwise logical-AND
               of x with the value of the mask formed from the
               corresponding index object inetCidrRoutePfxLen MUST be
               equal to x.  If not, then the index pair is not
               consistent and an inconsistentName error must be
               returned on SET or CREATE requests.";
            smi:oid "1.3.6.1.2.1.4.24.7.1.2";
         }

         leaf inetCidrRoutePfxLen {
            type inet-address:InetAddressPrefixLength;
            config false;
            description   
              "Indicates the number of leading one bits that form the
               mask to be logical-ANDed with the destination address
               before being compared to the value in the
               
               
               
               inetCidrRouteDest field.
               
               The values for the index objects inetCidrRouteDest and
               inetCidrRoutePfxLen must be consistent.  When the value
               of inetCidrRouteDest (excluding the zone index, if one
               is present) is x, then the bitwise logical-AND
               of x with the value of the mask formed from the
               corresponding index object inetCidrRoutePfxLen MUST be
               equal to x.  If not, then the index pair is not
               consistent and an inconsistentName error must be
               returned on SET or CREATE requests.";
            smi:oid "1.3.6.1.2.1.4.24.7.1.3";
         }

         leaf inetCidrRoutePolicy {
            type yang:object-identifier;
            config false;
            description   
              "This object is an opaque object without any defined
               semantics.  Its purpose is to serve as an additional
               index that may delineate between multiple entries to
               the same destination.  The value { 0 0 } shall be used
               as the default value for this object.";
            smi:oid "1.3.6.1.2.1.4.24.7.1.4";
         }

         leaf inetCidrRouteNextHopType {
            type inet-address:InetAddressType;
            config false;
            description   
              "The type of the inetCidrRouteNextHop address, as
               defined in the InetAddress MIB.
               
               Value should be set to unknown(0) for non-remote
               routes.
               
               Only those address types that may appear in an actual
               routing table are allowed as values of this object.";
            reference 
              "RFC 4001";
            smi:oid "1.3.6.1.2.1.4.24.7.1.5";
         }

         leaf inetCidrRouteNextHop {
            type inet-address:InetAddress;
            config false;
            description   
              "On remote routes, the address of the next system en
               
               
               
               route.  For non-remote routes, a zero length string.
               
               The type of this address is determined by the value of
               the inetCidrRouteNextHopType object.";
            smi:oid "1.3.6.1.2.1.4.24.7.1.6";
         }

         leaf inetCidrRouteIfIndex {
            type if-mib:InterfaceIndexOrZero;
            config true;
            description   
              "The ifIndex value that identifies the local interface
               through which the next hop of this route should be
               reached.  A value of 0 is valid and represents the
               scenario where no interface is specified.";
            smi:oid "1.3.6.1.2.1.4.24.7.1.7";
         }

         leaf inetCidrRouteType {
            type enumeration {
               enum other     { value 1; }
               enum reject    { value 2; }
               enum local     { value 3; }
               enum remote    { value 4; }
               enum blackhole { value 5; }
            }
            config true;
            description   
              "The type of route.  Note that local(3) refers to a
               route for which the next hop is the final destination;
               remote(4) refers to a route for which the next hop is
               not the final destination.
               
               Routes that do not result in traffic forwarding or
               rejection should not be displayed, even if the
               implementation keeps them stored internally.
               
               reject(2) refers to a route that, if matched, discards
               the message as unreachable and returns a notification
               (e.g., ICMP error) to the message sender.  This is used
               in some protocols as a means of correctly aggregating
               routes.
               
               blackhole(5) refers to a route that, if matched,
               discards the message silently.";
            smi:oid "1.3.6.1.2.1.4.24.7.1.8";
         }

         leaf inetCidrRouteProto {
            type iana-rtproto:IANAipRouteProtocol;
            config false;
            description   
              "The routing mechanism via which this route was learned.
               Inclusion of values for gateway routing protocols is
               not intended to imply that hosts should support those
               protocols.";
            smi:oid "1.3.6.1.2.1.4.24.7.1.9";
         }

         leaf inetCidrRouteAge {
            type yang:gauge32;
            config false;
            description   
              "The number of seconds since this route was last updated
               or otherwise determined to be correct.  Note that no
               semantics of 'too old' can be implied, except through
               knowledge of the routing protocol by which the route
               was learned.";
            smi:oid "1.3.6.1.2.1.4.24.7.1.10";
         }

         leaf inetCidrRouteNextHopAS {
            type inet-address:InetAutonomousSystemNumber;
            config true;
            description   
              "The Autonomous System Number of the Next Hop.  The
               semantics of this object are determined by the routing-
               protocol specified in the route's inetCidrRouteProto
               value.  When this object is unknown or not relevant, its
               value should be set to zero.";
            smi:default "0";
            smi:oid "1.3.6.1.2.1.4.24.7.1.11";
         }

         leaf inetCidrRouteMetric1 {
            type int32;
            config true;
            description   
              "The primary routing metric for this route.  The
               semantics of this metric are determined by the routing-
               protocol specified in the route's inetCidrRouteProto
               value.  If this metric is not used, its value should be
               set to -1.";
            smi:default "-1";
            smi:oid "1.3.6.1.2.1.4.24.7.1.12";
         }

         leaf inetCidrRouteMetric2 {
            type int32;
            config true;
            description   
              "An alternate routing metric for this route.  The
               semantics of this metric are determined by the routing-
               protocol specified in the route's inetCidrRouteProto
               value.  If this metric is not used, its value should be
               set to -1.";
            smi:default "-1";
            smi:oid "1.3.6.1.2.1.4.24.7.1.13";
         }

         leaf inetCidrRouteMetric3 {
            type int32;
            config true;
            description   
              "An alternate routing metric for this route.  The
               semantics of this metric are determined by the routing-
               protocol specified in the route's inetCidrRouteProto
               value.  If this metric is not used, its value should be
               set to -1.";
            smi:default "-1";
            smi:oid "1.3.6.1.2.1.4.24.7.1.14";
         }

         leaf inetCidrRouteMetric4 {
            type int32;
            config true;
            description   
              "An alternate routing metric for this route.  The
               semantics of this metric are determined by the routing-
               protocol specified in the route's inetCidrRouteProto
               value.  If this metric is not used, its value should be
               set to -1.";
            smi:default "-1";
            smi:oid "1.3.6.1.2.1.4.24.7.1.15";
         }

         leaf inetCidrRouteMetric5 {
            type int32;
            config true;
            description   
              "An alternate routing metric for this route.  The
               semantics of this metric are determined by the routing-
               
               
               
               protocol specified in the route's inetCidrRouteProto
               value.  If this metric is not used, its value should be
               set to -1.";
            smi:default "-1";
            smi:oid "1.3.6.1.2.1.4.24.7.1.16";
         }

         leaf inetCidrRouteStatus {
            type smiv2:RowStatus;
            config true;
            description   
              "The row status variable, used according to row
               installation and removal conventions.
               
               A row entry cannot be modified when the status is
               marked as active(1).";
            smi:oid "1.3.6.1.2.1.4.24.7.1.17";
         }
      }

      leaf inetCidrRouteDiscards {
         type yang:counter32;
         config false;
         description 
           "The number of valid route entries discarded from the
            inetCidrRouteTable.  Discarded route entries do not
            appear in the inetCidrRouteTable.  One possible reason
            for discarding an entry would be to free-up buffer space
            for other route table entries.";
         smi:oid "1.3.6.1.2.1.4.24.8";
      }
      smi:oid "1.3.6.1.2.1.4.24";
   }

} /* end of module IP-FORWARD-MIB */
