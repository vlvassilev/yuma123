module mod1 {

    namespace "http://example.com/ns/identityref-submodule-2-m1";

    prefix "m1";

    include sub1;

    organization  "example.com";

    description 
      "Testing identityref leaf defined in included submodule.";

    revision 2020-04-10 {
        description
            "Initial.";
    }
}
