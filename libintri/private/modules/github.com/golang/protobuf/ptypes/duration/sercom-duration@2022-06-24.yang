module sercom-duration {

  namespace "sercom:sercom-duration";
  prefix "sercom-duration";
  organization "
    Sercomm Inc.";
  contact "
    sercomm@sercomm.com.tw";
  revision 2022-06-24 {
    description "Build date.";
  }

  grouping Duration {
    leaf Seconds {
      mandatory "true";
      type int64;
    }
    leaf Nanos {
      mandatory "true";
      type int32;
    }
  }
}
