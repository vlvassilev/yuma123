module siltest3 {

    namespace "http://netconfcentral.org/ns/siltest3";
    prefix "siltest3";

    description 
      "Test SIL code generation for nested lists and union types.";

    revision 2011-09-16 {
       description "Initial version.";
    }

    list u {
      key ux;
      leaf ux { 
        type union {
          type uint32; 
          type string;
        }
      }
      leaf uy { type uint32; }
      leaf uz { config false; type uint32; }
      leaf uu { 
        config false; 
        type union {
          type int32;
          type instance-identifier;
          type uint8;
          type boolean;
        }
      }
    }

    list c {
       key x;
       leaf x { type uint16; }
       leaf y { type instance-identifier; }
       leaf z { type uint64; config false; }
       leaf cuu { 
         type union {
           type int32;
           type instance-identifier;
           type uint8;
           type boolean;
           type string;
         }
       }
       list cc {
          key xx;
          leaf xx { 
            type union {
              type uint32; 
              type string;
            }
          }
          leaf yy { type int32; }
          leaf zz { type uint64; config false; }
          list ccc {
             key xxx;
             leaf xxx { type string; }
             leaf yyy { type boolean; }
             leaf zzz { type uint64; config false; }
          }
       }
    }

    identity x;

    rpc r { 
      input {
        leaf a { type string; }
        leaf b { type int8; }
      }
      output {
        leaf c { type int64; }
        leaf d { type identityref { base x; } }
      } 
    }

    notification n { 
      leaf a { type binary; }
      leaf b { type instance-identifier; }
      leaf c { type int64; }
      leaf d { type identityref { base x; } }
    }



}
