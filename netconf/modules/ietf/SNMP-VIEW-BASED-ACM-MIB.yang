/*
 * This module has been generated by smidump 0.4.6:
 *
 *      smidump -f yang --yang-smi-extensions SNMP-VIEW-BASED-ACM-MIB
 *
 * Do not edit. Edit the source file instead!
 */

module SNMP-VIEW-BASED-ACM-MIB {

   /*** NAMESPACE / PREFIX DEFINITION ***/

   namespace "urn:ietf:params:xml:ns:yang:smiv2:SNMP-VIEW-BASED-ACM-MIB";
   prefix "snmp-view";

   /*** LINKAGE (IMPORTS / INCLUDES) ***/

   import SNMP-FRAMEWORK-MIB { prefix "snmp-framework"; }
   import SNMPv2-TC          { prefix "smiv2"; }
   import yang-smi           { prefix "smi"; }
   import yang-types         { prefix "yang"; }

   /*** META INFORMATION ***/

   organization     
     "SNMPv3 Working Group";

   contact          
     "WG-email:   snmpv3@lists.tislabs.com
      Subscribe:  majordomo@lists.tislabs.com
                  In message body:  subscribe snmpv3
      
      Co-Chair:   Russ Mundy
                  Network Associates Laboratories
      postal:     15204 Omega Drive, Suite 300
                  Rockville, MD 20850-4601
                  USA
      email:      mundy@tislabs.com
      phone:      +1 301-947-7107
      
      Co-Chair:   David Harrington
                  Enterasys Networks
      Postal:     35 Industrial Way
                  P. O. Box 5004
                  Rochester, New Hampshire 03866-5005
                  USA
      EMail:      dbh@enterasys.com
      Phone:      +1 603-337-2614
      
      Co-editor:  Bert Wijnen
                  Lucent Technologies
      postal:     Schagen 33
                  3461 GL Linschoten
                  Netherlands
      email:      bwijnen@lucent.com
      phone:      +31-348-480-685
      
      Co-editor:  Randy Presuhn
                  BMC Software, Inc.
      
      postal:     2141 North First Street
                  San Jose, CA 95131
                  USA
      email:      randy_presuhn@bmc.com
      phone:      +1 408-546-1006
      
      Co-editor:  Keith McCloghrie
                  Cisco Systems, Inc.
      postal:     170 West Tasman Drive
                  San Jose, CA  95134-1706
                  USA
      email:      kzm@cisco.com
      phone:      +1-408-526-5260";

   description      
     "The management information definitions for the
      View-based Access Control Model for SNMP.
      
      Copyright (C) The Internet Society (2002). This
      version of this MIB module is part of RFC 3415;
      see the RFC itself for full legal notices.";

   revision "2002-10-16" {
      description   
        "Clarifications, published as RFC3415";
   }
   revision "1999-01-20" {
      description   
        "Clarifications, published as RFC2575";
   }
   revision "1997-11-20" {
      description   
        "Initial version, published as RFC2275";
   }

   container vacmMIBObjects {


      /* XXX table comments here XXX */

      list vacmContextEntry {

         key "vacmContextName";
         description 
           "Information about a particular context.";
         smi:oid "1.3.6.1.6.3.16.1.1.1";


         leaf vacmContextName {
            type snmp-framework:SnmpAdminString {
               length "0..32";
            }
            config false;
            description   
              "A human readable name identifying a particular
               context at a particular SNMP entity.
               
               The empty contextName (zero length) represents the
               default context.";
            smi:oid "1.3.6.1.6.3.16.1.1.1.1";
         }
      }


      /* XXX table comments here XXX */

      list vacmSecurityToGroupEntry {

         key "vacmSecurityModel vacmSecurityName";
         description 
           "An entry in this table maps the combination of a
            securityModel and securityName into a groupName.";
         smi:oid "1.3.6.1.6.3.16.1.2.1";


         leaf vacmSecurityModel {
            type snmp-framework:SnmpSecurityModel {
               range "1..2147483647";
            }
            config false;
            description   
              "The Security Model, by which the vacmSecurityName
               referenced by this entry is provided.
               
               Note, this object may not take the 'any' (0) value.";
            smi:oid "1.3.6.1.6.3.16.1.2.1.1";
         }

         leaf vacmSecurityName {
            type snmp-framework:SnmpAdminString {
               length "1..32";
            }
            config false;
            description   
              "The securityName for the principal, represented in a
               Security Model independent format, which is mapped by
               this entry to a groupName.";
            smi:oid "1.3.6.1.6.3.16.1.2.1.2";
         }

         leaf vacmGroupName {
            type snmp-framework:SnmpAdminString {
               length "1..32";
            }
            config true;
            description   
              "The name of the group to which this entry (e.g., the
               combination of securityModel and securityName)
               belongs.
               
               This groupName is used as index into the
               vacmAccessTable to select an access control policy.
               However, a value in this table does not imply that an
               instance with the value exists in table vacmAccesTable.";
            smi:oid "1.3.6.1.6.3.16.1.2.1.3";
         }

         leaf vacmSecurityToGroupStorageType {
            type smiv2:StorageType;
            config true;
            description   
              "The storage type for this conceptual row.
               Conceptual rows having the value 'permanent' need not
               allow write-access to any columnar objects in the row.";
            smi:default "nonVolatile";
            smi:oid "1.3.6.1.6.3.16.1.2.1.4";
         }

         leaf vacmSecurityToGroupStatus {
            type smiv2:RowStatus;
            config true;
            description   
              "The status of this conceptual row.
               
               Until instances of all corresponding columns are
               appropriately configured, the value of the
               
               corresponding instance of the vacmSecurityToGroupStatus
               column is 'notReady'.
               
               In particular, a newly created row cannot be made
               active until a value has been set for vacmGroupName.
               
               The  RowStatus TC [RFC2579] requires that this
               DESCRIPTION clause states under which circumstances
               other objects in this row can be modified:
               
               The value of this object has no effect on whether
               other objects in this conceptual row can be modified.";
            smi:oid "1.3.6.1.6.3.16.1.2.1.5";
         }
      }


      /* XXX table comments here XXX */

      list vacmAccessEntry {

         key "vacmGroupName vacmAccessContextPrefix 
              vacmAccessSecurityModel vacmAccessSecurityLevel";
         description 
           "An access right configured in the Local Configuration
            Datastore (LCD) authorizing access to an SNMP context.
            
            Entries in this table can use an instance value for
            object vacmGroupName even if no entry in table
            vacmAccessSecurityToGroupTable has a corresponding
            value for object vacmGroupName.";
         smi:oid "1.3.6.1.6.3.16.1.4.1";

         leaf vacmGroupName {
            type leafref {
               path "/snmp-view:vacmMIBObjects/snmp-view:vacmSecurityToGroupEntry/snmp-view:vacmGroupName";
            }
            config true;
            description   
              "Automagically generated leafref leaf.";
         }

         leaf vacmAccessContextPrefix {
            type snmp-framework:SnmpAdminString {
               length "0..32";
            }
            config false;
            description   
              "In order to gain the access rights allowed by this
               conceptual row, a contextName must match exactly
               (if the value of vacmAccessContextMatch is 'exact')
               or partially (if the value of vacmAccessContextMatch
               is 'prefix') to the value of the instance of this
               object.";
            smi:oid "1.3.6.1.6.3.16.1.4.1.1";
         }

         leaf vacmAccessSecurityModel {
            type snmp-framework:SnmpSecurityModel;
            config false;
            description   
              "In order to gain the access rights allowed by this
               conceptual row, this securityModel must be in use.";
            smi:oid "1.3.6.1.6.3.16.1.4.1.2";
         }

         leaf vacmAccessSecurityLevel {
            type snmp-framework:SnmpSecurityLevel;
            config false;
            description   
              "The minimum level of security required in order to
               gain the access rights allowed by this conceptual
               row.  A securityLevel of noAuthNoPriv is less than
               authNoPriv which in turn is less than authPriv.
               
               If multiple entries are equally indexed except for
               this vacmAccessSecurityLevel index, then the entry
               which has the highest value for
               vacmAccessSecurityLevel is selected.";
            smi:oid "1.3.6.1.6.3.16.1.4.1.3";
         }

         leaf vacmAccessContextMatch {
            type enumeration {
               enum exact  { value 1; }
               enum prefix { value 2; }
            }
            config true;
            description   
              "If the value of this object is exact(1), then all
               rows where the contextName exactly matches
               vacmAccessContextPrefix are selected.
               
               If the value of this object is prefix(2), then all
               rows where the contextName whose starting octets
               exactly match vacmAccessContextPrefix are selected.
               This allows for a simple form of wildcarding.";
            smi:default "exact";
            smi:oid "1.3.6.1.6.3.16.1.4.1.4";
         }

         leaf vacmAccessReadViewName {
            type snmp-framework:SnmpAdminString {
               length "0..32";
            }
            config true;
            description   
              "The value of an instance of this object identifies
               the MIB view of the SNMP context to which this
               conceptual row authorizes read access.
               
               The identified MIB view is that one for which the
               vacmViewTreeFamilyViewName has the same value as the
               instance of this object; if the value is the empty
               string or if there is no active MIB view having this
               value of vacmViewTreeFamilyViewName, then no access
               is granted.";
            smi:default "";
            smi:oid "1.3.6.1.6.3.16.1.4.1.5";
         }

         leaf vacmAccessWriteViewName {
            type snmp-framework:SnmpAdminString {
               length "0..32";
            }
            config true;
            description   
              "The value of an instance of this object identifies
               the MIB view of the SNMP context to which this
               conceptual row authorizes write access.
               
               The identified MIB view is that one for which the
               vacmViewTreeFamilyViewName has the same value as the
               instance of this object; if the value is the empty
               string or if there is no active MIB view having this
               value of vacmViewTreeFamilyViewName, then no access
               is granted.";
            smi:default "";
            smi:oid "1.3.6.1.6.3.16.1.4.1.6";
         }

         leaf vacmAccessNotifyViewName {
            type snmp-framework:SnmpAdminString {
               length "0..32";
            }
            config true;
            description   
              "The value of an instance of this object identifies
               the MIB view of the SNMP context to which this
               conceptual row authorizes access for notifications.
               
               The identified MIB view is that one for which the
               vacmViewTreeFamilyViewName has the same value as the
               instance of this object; if the value is the empty
               string or if there is no active MIB view having this
               value of vacmViewTreeFamilyViewName, then no access
               is granted.";
            smi:default "";
            smi:oid "1.3.6.1.6.3.16.1.4.1.7";
         }

         leaf vacmAccessStorageType {
            type smiv2:StorageType;
            config true;
            description   
              "The storage type for this conceptual row.
               
               Conceptual rows having the value 'permanent' need not
               allow write-access to any columnar objects in the row.";
            smi:default "nonVolatile";
            smi:oid "1.3.6.1.6.3.16.1.4.1.8";
         }

         leaf vacmAccessStatus {
            type smiv2:RowStatus;
            config true;
            description   
              "The status of this conceptual row.
               
               The  RowStatus TC [RFC2579] requires that this
               DESCRIPTION clause states under which circumstances
               other objects in this row can be modified:
               
               The value of this object has no effect on whether
               other objects in this conceptual row can be modified.";
            smi:oid "1.3.6.1.6.3.16.1.4.1.9";
         }
      }

      smi:oid "1.3.6.1.6.3.16.1";
   }

   container vacmMIBViews {

      leaf vacmViewSpinLock {
         type smiv2:TestAndIncr;
         config true;
         description 
           "An advisory lock used to allow cooperating SNMP
            Command Generator applications to coordinate their
            use of the Set operation in creating or modifying
            views.
            
            When creating a new view or altering an existing
            view, it is important to understand the potential
            interactions with other uses of the view.  The
            vacmViewSpinLock should be retrieved.  The name of
            the view to be created should be determined to be
            unique by the SNMP Command Generator application by
            consulting the vacmViewTreeFamilyTable.  Finally,
            the named view may be created (Set), including the
            advisory lock.
            If another SNMP Command Generator application has
            altered the views in the meantime, then the spin
            lock's value will have changed, and so this creation
            will fail because it will specify the wrong value for
            the spin lock.
            
            Since this is an advisory lock, the use of this lock
            is not enforced.";
         smi:oid "1.3.6.1.6.3.16.1.5.1";
      }


      /* XXX table comments here XXX */

      list vacmViewTreeFamilyEntry {

         key "vacmViewTreeFamilyViewName 
              vacmViewTreeFamilySubtree";
         description 
           "Information on a particular family of view subtrees
            included in or excluded from a particular SNMP
            context's MIB view.
            
            Implementations must not restrict the number of
            families of view subtrees for a given MIB view,
            except as dictated by resource constraints on the
            overall number of entries in the
            vacmViewTreeFamilyTable.
            
            If no conceptual rows exist in this table for a given
            MIB view (viewName), that view may be thought of as
            consisting of the empty set of view subtrees.";
         smi:oid "1.3.6.1.6.3.16.1.5.2.1";


         leaf vacmViewTreeFamilyViewName {
            type snmp-framework:SnmpAdminString {
               length "1..32";
            }
            config false;
            description   
              "The human readable name for a family of view subtrees.";
            smi:oid "1.3.6.1.6.3.16.1.5.2.1.1";
         }

         leaf vacmViewTreeFamilySubtree {
            type yang:object-identifier;
            config false;
            description   
              "The MIB subtree which when combined with the
               corresponding instance of vacmViewTreeFamilyMask
               defines a family of view subtrees.";
            smi:oid "1.3.6.1.6.3.16.1.5.2.1.2";
         }

         leaf vacmViewTreeFamilyMask {
            type binary {
               length "0..16";
            }
            config true;
            description   
              "The bit mask which, in combination with the
               corresponding instance of vacmViewTreeFamilySubtree,
               defines a family of view subtrees.
               
               Each bit of this bit mask corresponds to a
               sub-identifier of vacmViewTreeFamilySubtree, with the
               most significant bit of the i-th octet of this octet
               string value (extended if necessary, see below)
               corresponding to the (8*i - 7)-th sub-identifier, and
               the least significant bit of the i-th octet of this
               octet string corresponding to the (8*i)-th
               sub-identifier, where i is in the range 1 through 16.
               
               Each bit of this bit mask specifies whether or not
               the corresponding sub-identifiers must match when
               determining if an OBJECT IDENTIFIER is in this
               family of view subtrees; a '1' indicates that an
               exact match must occur; a '0' indicates 'wild card',
               i.e., any sub-identifier value matches.
               
               Thus, the OBJECT IDENTIFIER X of an object instance
               is contained in a family of view subtrees if, for
               each sub-identifier of the value of
               vacmViewTreeFamilySubtree, either:
               
                 the i-th bit of vacmViewTreeFamilyMask is 0, or
               
                 the i-th sub-identifier of X is equal to the i-th
                 sub-identifier of the value of
                 vacmViewTreeFamilySubtree.
               
               If the value of this bit mask is M bits long and
               
               there are more than M sub-identifiers in the
               corresponding instance of vacmViewTreeFamilySubtree,
               then the bit mask is extended with 1's to be the
               required length.
               
               Note that when the value of this object is the
               zero-length string, this extension rule results in
               a mask of all-1's being used (i.e., no 'wild card'),
               and the family of view subtrees is the one view
               subtree uniquely identified by the corresponding
               instance of vacmViewTreeFamilySubtree.
               
               Note that masks of length greater than zero length
               do not need to be supported.  In this case this
               object is made read-only.";
            smi:default "";
            smi:oid "1.3.6.1.6.3.16.1.5.2.1.3";
         }

         leaf vacmViewTreeFamilyType {
            type enumeration {
               enum included { value 1; }
               enum excluded { value 2; }
            }
            config true;
            description   
              "Indicates whether the corresponding instances of
               vacmViewTreeFamilySubtree and vacmViewTreeFamilyMask
               define a family of view subtrees which is included in
               or excluded from the MIB view.";
            smi:default "included";
            smi:oid "1.3.6.1.6.3.16.1.5.2.1.4";
         }

         leaf vacmViewTreeFamilyStorageType {
            type smiv2:StorageType;
            config true;
            description   
              "The storage type for this conceptual row.
               
               Conceptual rows having the value 'permanent' need not
               allow write-access to any columnar objects in the row.";
            smi:default "nonVolatile";
            smi:oid "1.3.6.1.6.3.16.1.5.2.1.5";
         }

         leaf vacmViewTreeFamilyStatus {
            type smiv2:RowStatus;
            config true;
            description   
              "The status of this conceptual row.
               
               The  RowStatus TC [RFC2579] requires that this
               DESCRIPTION clause states under which circumstances
               other objects in this row can be modified:
               
               The value of this object has no effect on whether
               other objects in this conceptual row can be modified.";
            smi:oid "1.3.6.1.6.3.16.1.5.2.1.6";
         }
      }
      smi:oid "1.3.6.1.6.3.16.1.5";
   }

} /* end of module SNMP-VIEW-BASED-ACM-MIB */
