module iwl-test-event1 {

  namespace "http://www.iwl.com/netconf/ns/iwl-test-event1";

  prefix "iwl1";

  organization
    "Interworking Labs, Inc.";

  contact
    "Andy Bierman";

  description
    "YANG test module for IWL NETCONF Event 1";

  revision 2009-03-27 {
    description "Initial version.";
  }

  grouping Leafs.1 {

    leaf binary.1 {
       type binary;
    }

    leaf bits.1 {
       type bits {
         bit zero;
         bit one;
         bit two;
         bit ten { position 10; }
         bit last;
       }
    }

    leaf boolean.1 {
       type boolean;
    }

    /* this will be added in yang-05
     * leaf decimal64.1 {
     *   type decimal64 { fraction-digits 3; }
     * }
     */

    leaf empty.1 {
       type empty;
    }
    
    leaf enumeration.1 {
       type enumeration {
         enum red { value 5; }
         enum green { value 9; }
         enum blue { value 11; }
         enum 'deep purple' { value 17; }
       }
    }

    leaf identityref.1 {
       type identityref { base id-A; }
    }

    leaf instance-identifier.1 {
       type instance-identifier { 
         require-instance false; 
       }
    }

    leaf instance-identifier.2 {
       type instance-identifier { 
         require-instance true; 
       }
    }
    
    leaf int8.1 {
       type int8;
    }

    leaf int16.1 {
       type int16;
    }

    leaf int32.1 {
       type int32;
    }

    leaf int64.1 {
       type int64;
    }

    leaf leafref.1 {
       type leafref {
          path "../instance-identifier.1";
          require-instance true;
       }
    }

    leaf leafref.2 {
       type leafref {
          path "../string.1";
          require-instance false;
       }
    }

    leaf string.1 {
       type string;
    }

    leaf uint8.1 {
       type uint8;
    }

    leaf uint16.1 {
       type uint16;
    }

    leaf uint32.1 {
       type uint32;
    }

    leaf uint64.1 {
       type uint64;
    }

    leaf dec64.1 {
       type decimal64 {
         fraction-digits 4;
       }
    }

    leaf dec64.2 {
       type decimal64 {
         fraction-digits 2;
         range "0 .. 3 | 9 .. max";
       }
    }

    leaf dec64.3 {
       type decimal64 {
         fraction-digits 18;
	 range "3.1234567 .. max";
       }
    }
    
    leaf union.1 {
      type union {
        type int8;
        type binary;
        type string;
        type union {
          type boolean;
          type uint64;
       }
     }
   }
 }

 identity id-A;
 identity id-B { base id-A; }
 identity id-C { base id-B; }
 identity id-D { base id-C; }

 uses Leafs.1;

 container container.1 {
   uses Leafs.1;
 }

 container container.2 {
   presence "this is a presence container";
   uses Leafs.1;
 }

 list list.1 {
   key "string.1 uint32.1";
   uses Leafs.1;
 }

 choice choice.1 {
   case case.1.1 {
     leaf a { type string; }
     leaf b { type string; mandatory true; }
   }
   leaf c { type string; mandatory true; }
   leaf d { type binary; }
 }

}
