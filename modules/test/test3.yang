module test3 {

    namespace "urn:ietf:params:xml:ns:yang:test3";
    prefix "t3";


    revision 2008-10-19 {
        description "Initial revision.";
    }

    container test33 {
      choice f {
        mandatory true;

        leaf f1 { type string; }
        leaf f2 { type string; }
      }

      choice g {
        mandatory false;

        leaf g1 { type string; mandatory true; }
        leaf g2 { type string; }
        case g3 {
          leaf g3a { type string; mandatory true; }
          leaf g3b { type string; }
        }
      }
    }
}
