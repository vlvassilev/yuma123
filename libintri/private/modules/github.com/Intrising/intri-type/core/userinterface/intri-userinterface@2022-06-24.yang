module intri-userinterface {

  namespace "intri:intri-userinterface";
  prefix "intri-userinterface";
  organization "
    Intrising Inc.";
  contact "
    intrising@intrising.com.tw";
  revision 2022-06-24 {
    description "Build date.";
  }

  import intri-empty {
    prefix intri-empty;
  }
  import intri-common {
    prefix intri-common;
  }
  typedef SNMPV3ConfigSecurityModelTypeOptions {
    type enumeration {
      enum SNMP_V3_CONFIG_SECURITY_MODEL_USM {
        description "[USM] Assign the USM as the SNMPv3 security model";
        value 0;
      }
      enum SNMP_V3_CONFIG_SECURITY_MODEL_VACM {
        description "[VCAM] Assign the VACM as the SNMPv3 security model";
        value 1;
      }
      enum SNMP_V3_CONFIG_SECURITY_MODEL_TSM {
        description "[TSM] Assign the TSM as the SNMPv3 security model";
        value 2;
      }
    }
  }
  typedef WebProtocolTypeOptions {
    type enumeration {
      enum WEB_PROTOCOL_TYPE_DISABLED {
        description "[Disabled] Web interface is disabled";
        value 0;
      }
      enum WEB_PROTOCOL_TYPE_HTTP_UNSECURE {
        description "[HTTP Only] Standard client interface";
        value 1;
      }
      enum WEB_PROTOCOL_TYPE_HTTPS_SECURE {
        description "[HTTPS Only] Secure client interface";
        value 2;
      }
      enum WEB_PROTOCOL_TYPE_HTTP_AND_HTTPS {
        description "[HTTP & HTTPS] Both Standard & Secure client interface";
        value 3;
      }
    }
  }
  grouping CLIConfig {
    leaf TelnetEnabled {
      mandatory "true";
      type boolean;
    }
    leaf SSHEnabled {
      mandatory "true";
      type boolean;
    }
    leaf WelcomeMessage {
      mandatory "true";
      type string;
    }
    leaf InactivityTimeout {
      mandatory "true";
      type int32;
    }
  }
  grouping SNMPConfig {
    leaf SNMPV1Enabled {
      mandatory "true";
      type boolean;
    }
    leaf SNMPV2CEnabled {
      mandatory "true";
      type boolean;
    }
    leaf GetCommunity {
      mandatory "true";
      type string;
    }
    leaf SetCommunity {
      mandatory "true";
      type string;
    }
    leaf SNMPV1V2Username {
      mandatory "true";
      type string;
    }
    leaf PermitV1V2SetCommands {
      mandatory "true";
      type boolean;
    }
    leaf SNMPV3Enabled {
      mandatory "true";
      type boolean;
    }
    leaf SecurityModel {
      mandatory "true";
      type SNMPV3ConfigSecurityModelTypeOptions;
    }
    leaf SNMPEngineID {
      mandatory "true";
      type string;
    }
    leaf TrapEngineID {
      mandatory "true";
      type string;
    }
  }
  grouping WebConfig {
    leaf Protocol {
      mandatory "true";
      type WebProtocolTypeOptions;
    }
    leaf WebTimeout {
      mandatory "true";
      type int32;
    }
    leaf HTTPPort {
      mandatory "true";
      type int32;
    }
    leaf HTTPSPort {
      mandatory "true";
      type int32;
    }
    leaf EncryptedCertPassphrase {
      mandatory "true";
      type string;
    }
    leaf LoginMessage {
      mandatory "true";
      type string;
    }
  }
  grouping Config {
    container Cli {
      uses CLIConfig;
    }
    container Snmp {
      uses SNMPConfig;
    }
    container Web {
      uses WebConfig;
    }
  }
  rpc intri-userinterface-UserInterface-GetConfig {
    output {
      uses Config;
    }
  }
  rpc intri-userinterface-UserInterface-GetCLIConfig {
    output {
      uses CLIConfig;
    }
  }
  rpc intri-userinterface-UserInterface-SetCLIConfig {
    input {
      uses CLIConfig;
    }
  }
  rpc intri-userinterface-UserInterface-GetWebConfig {
    output {
      uses WebConfig;
    }
  }
  rpc intri-userinterface-UserInterface-SetWebConfig {
    input {
      uses WebConfig;
    }
  }
  rpc intri-userinterface-UserInterface-RunRestartWebServer {
    input {
      uses intri-common:Confirm;
    }
  }
  rpc intri-userinterface-UserInterface-GetSNMPConfig {
    output {
      uses SNMPConfig;
    }
  }
  rpc intri-userinterface-UserInterface-SetSNMPConfig {
    input {
      uses SNMPConfig;
    }
  }
  rpc intri-userinterface-UserInterface-RunRestartSNMPServer {
    input {
      uses intri-common:Confirm;
    }
  }
}
