module intri-timerange {

  namespace "intri:intri-timerange";
  prefix "intri-timerange";
  organization "
    Intrising Inc.";
  contact "
    intrising@intrising.com.tw";
  revision 2022-06-24 {
    description "Build date.";
  }

  import intri-timeofday {
    prefix intri-timeofday;
  }
  import intri-date {
    prefix intri-date;
  }
  import intri-dayofweek {
    prefix intri-dayofweek;
  }
  import intri-empty {
    prefix intri-empty;
  }
  import intri-common {
    prefix intri-common;
  }
  typedef CommandTypeOptions {
    type enumeration {
      enum COMMAND_TYPE_PERIODIC {
        description "[Periodic]";
        value 0;
      }
      enum COMMAND_TYPE_ABSOLUTE {
        description "[Absolute]";
        value 1;
      }
    }
  }
  typedef PeriodicDayTypeOptions {
    type enumeration {
      enum PERIODIC_DAY_TYPE_DAYOFWEEK {
        description "[Day of the week]";
        value 0;
      }
      enum PERIODIC_DAY_TYPE_DAILY {
        description "[Daily]";
        value 1;
      }
      enum PERIODIC_DAY_TYPE_WEEKDAYS {
        description "[Weekdays]";
        value 2;
      }
      enum PERIODIC_DAY_TYPE_WEEKEND {
        description "[Weekend]";
        value 3;
      }
    }
  }
  grouping Config {
    container List {
      list List_Entry {
        uses ConfigEntry;
      }
    }
  }
  grouping ConfigEntry {
    leaf Name {
      mandatory "true";
      type string;
    }
    leaf Enabled {
      mandatory "true";
      type boolean;
    }
    leaf Command {
      mandatory "true";
      type CommandTypeOptions;
    }
    container PeriodicDay {
      uses DayTime;
    }
    container StartTime {
      uses intri-timeofday:TimeOfDay;
    }
    container EndTime {
      uses intri-timeofday:TimeOfDay;
    }
    container StartDate {
      uses intri-date:Date;
    }
    container EndDate {
      uses intri-date:Date;
    }
  }
  grouping DayTime {
    leaf PeriodicType {
      mandatory "true";
      type PeriodicDayTypeOptions;
    }
    container DayOfWeekLists {
      leaf-list DayOfWeekLists_Entry {
        type intri-dayofweek:DayOfWeek;
      }
    }
  }
  grouping EntryStatus {
    leaf Name {
      mandatory "true";
      type string;
    }
    leaf IsActive {
      mandatory "true";
      type boolean;
    }
  }
  grouping Status {
    container List {
      list List_Entry {
        uses EntryStatus;
      }
    }
  }
  rpc intri-timerange-TimeRange-GetConfig {
    output {
      uses Config;
    }
  }
  rpc intri-timerange-TimeRange-GetStatus {
    output {
      uses Status;
    }
  }
  rpc intri-timerange-TimeRange-AddTimeRange {
    input {
      uses ConfigEntry;
    }
  }
  rpc intri-timerange-TimeRange-DeleteTimeRange {
    input {
      uses intri-common:Name;
    }
  }
  rpc intri-timerange-TimeRange-UpdateTimeRange {
    input {
      uses ConfigEntry;
    }
  }
}
