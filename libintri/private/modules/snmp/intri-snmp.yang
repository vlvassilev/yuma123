module intri-snmp {
  namespace "intri:intri-snmp";
  prefix "intri-snmp";
  organization "Intrising Inc.";
  contact "xxx@intrising.com.tw";
  revision 2022-06-14 {
    description "Build date.";
  }
}
