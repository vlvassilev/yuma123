module yt12 {

   namespace "urn:ietf:params:xml:ns:yang:yt12";

   prefix "yt12";

   import ieee-types { prefix ieee; }
   import yang-types { prefix yt; }


   organization "Netconf Central";

   contact "Andy Bierman";

   description "YANG test module 12. yangdiff test";

   revision 2008-04-11 { description "initial version"; }

   leaf a1 { type int32; }

   container con1 {
      leaf a2 { type string; }
   }

   extension e1 {
      description "extension test";
      argument foo {
         yin-element true;
      }
   }

   leaf x { 
      type int32; 
   }

   grouping foo;

   grouping bar;

   extension bar;

   typedef error-1 {
      type int32;
   }

   typedef my-str-type {
     type string {
       length "1..255";
     }
     default "fred flintstone";
     status current;
     description "type description";
     reference "type external references";
   }

   typedef my-bits-type {
     type bits {
       bit 'x1';
       bit 'x2' { description "some bit"; }
     }
   }


   typedef my-enum-type {
     type enumeration {
       enum 'x 1';
       enum '2' { description "some enum"; }
     }
   }

    list order-test {
      key l1;
      leaf l1 { type string; }   
      leaf l2 { type string; }   
      leaf l3 { type string; }   
      leaf l4 { type string; }   
      leaf l5 { type string; } 
    }

}
