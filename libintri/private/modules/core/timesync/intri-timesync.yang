module intri-timesync {
  namespace "intri:intri-timesync";
  prefix "intri-timesync";
  import timesyncpb {
    prefix "timesyncpb";
  }
  import devicepb {
    prefix "devicepb";
  }
  organization "Intrising Inc.";
  contact "xxx@intrising.com.tw";
  revision 2022-06-14 {
    description "Build date.";
  }
}
