module mod1 {
  yang-version 1.1;

  namespace "http://yuma123.org/ns/test/yangcli/identical-node-names/mod1";
  prefix m1;

  organization
    "yuma123.org";

  description
    'Validation of handling of siblings with
     identical names but different module namespace.';

  revision 2018-04-16 {
    description
      "Initial version";
  }

  container bar {
    presence "/mod1:bar is present";
  }

  container foo {
    choice choice1 {
      case case1 {
        leaf foo {
          type string;
        }
        leaf bar {
          type string;
        }
      }
    }
  }
}
