// Code generated by protoc-gen-yang. DO NOT EDIT.


/* ****************************************************************************************************
 * Import Path : "github.com/Intrising/intri-type/core/dhcpserver"                                    *
 * Dir Path    : github.com/Intrising/intri-type/core/dhcpserver                                      *
 * Go Package  : dhcpserver                                                                           *
 * Files       : 3                                                                                    *
 **************************************************************************************************** */
module intri-dhcpserver {

  namespace "intri:intri-dhcpserver";

  prefix "intri-dhcpserver";

  organization "Intrising Inc.";

  contact "intrising@intrising.com.tw";

  revision 2022-06-23 {
    description "Build date.";
  }

  import intri-device {
    prefix intri-device;
  }
  import intri-empty {
    prefix intri-empty;
  }


  /* **************************************************************************************************
   * Enums       : 2                                                                                  *
   ************************************************************************************************** */
  /* core/dhcpserver/common.proto */
  typedef PoolTypeOptions {
    type enumeration {
      enum POOL_TYPE_BASIC {
        description "";
        value 0;
      }
      enum POOL_TYPE_MAC_BASED {
        description "";
        value 1;
      }
      enum POOL_TYPE_PORT_BASED {
        description "";
        value 2;
      }
    }
  }
  /* core/dhcpserver/common.proto */
  typedef InterfaceType {
    type enumeration {
      enum INTERFACE_TYPE_PORT {
        description "[Port] Select a port as the interface";
        value 0;
      }
      enum INTERFACE_TYPE_VLAN {
        description "[VLAN] Select a VLAN as the interface";
        value 1;
      }
    }
  }


  /* **************************************************************************************************
   * Msgs        : 10                                                                                 *
   ************************************************************************************************** */
  /* core/dhcpserver/dhcpserver.proto */
  grouping Config {
    container V4 {
      uses V4Config;
    }
  }
  /* core/dhcpserver/dhcpserver.proto */
  grouping V4Config {
    container Sys {
      uses System;
    }
    container Pool {
      uses Pool;
    }
  }
  /* core/dhcpserver/dhcpserver.proto */
  grouping System {
    leaf Enabled {
      type boolean;
    }
  }
  /* core/dhcpserver/dhcpserver.proto */
  grouping Pool {
    container List {
      list List_Entry {
        uses PoolEntry;
      }
    }
  }
  /* core/dhcpserver/dhcpserver.proto */
  grouping PoolEntry {
    leaf Name {
      type string;
    }
    container Interface {
      uses intri-device:InterfaceIdentify;
    }
    leaf EntryType {
      type PoolTypeOptions;
    }
    container Basic {
      uses Basic;
    }
    container MACBased {
      uses MACBased;
    }
    container PortBased {
      uses PortBased;
    }
    leaf ID {
      type string;
    }
  }
  /* core/dhcpserver/dhcpserver.proto */
  grouping Basic {
    leaf RangeLow {
      type string;
    }
    leaf RangeHigh {
      type string;
    }
    leaf Netmask {
      type string;
    }
    leaf Gateway {
      type string;
    }
    leaf PrimaryDNS {
      type string;
    }
    leaf SecondaryDNS {
      type string;
    }
    leaf LeaseTime {
      type int32;
    }
  }
  /* core/dhcpserver/dhcpserver.proto */
  grouping MACBased {
    leaf MACAddress {
      type string;
    }
    leaf DesiredIP {
      type string;
    }
  }
  /* core/dhcpserver/dhcpserver.proto */
  grouping PortBased {
    leaf PortNo {
      type int32;
    }
    leaf Ignore {
      type boolean;
    }
    leaf DesiredIP {
      type string;
    }
  }
  /* core/dhcpserver/dhcpserver.proto */
  grouping StatusEntry {
    leaf Name {
      type string;
    }
    container Interface {
      uses intri-device:InterfaceIdentify;
    }
    leaf PortNo {
      type int32;
    }
    leaf MACAddress {
      type string;
    }
    leaf IPAddress {
      type string;
    }
    leaf AvailableLeaseTime {
      type int32;
    }
  }
  /* core/dhcpserver/dhcpserver.proto */
  grouping Status {
    container List {
      list List_Entry {
        uses StatusEntry;
      }
    }
  }


  /* **************************************************************************************************
   * Services    : 1                                                                                  *
   ************************************************************************************************** */

  /* **************************************************************************************************
   * Service     : DHCPServer                                                                         *
   * Methods     : 12                                                                                 *
   ************************************************************************************************** */
  /* core/dhcpserver/service.proto */
  rpc intri-dhcpserver-GetV4Config {
    output  {
      uses V4Config;
    }
  }
  /* core/dhcpserver/service.proto */
  rpc intri-dhcpserver-SetV4System {
    input  {
      uses System;
    }
  }
  /* core/dhcpserver/service.proto */
  rpc intri-dhcpserver-AddV4Basic {
    input  {
      uses Pool;
    }
  }
  /* core/dhcpserver/service.proto */
  rpc intri-dhcpserver-UpdateV4Basic {
    input  {
      uses Pool;
    }
  }
  /* core/dhcpserver/service.proto */
  rpc intri-dhcpserver-DeleteV4Basic {
    input  {
      uses Pool;
    }
  }
  /* core/dhcpserver/service.proto */
  rpc intri-dhcpserver-GetV4Status {
    output  {
      uses Status;
    }
  }
  /* core/dhcpserver/service.proto */
  rpc intri-dhcpserver-GetV4MACBased {
    output  {
      uses Pool;
    }
  }
  /* core/dhcpserver/service.proto */
  rpc intri-dhcpserver-AddV4MACBased {
    input  {
      uses Pool;
    }
  }
  /* core/dhcpserver/service.proto */
  rpc intri-dhcpserver-DeleteV4MACBased {
    input  {
      uses Pool;
    }
  }
  /* core/dhcpserver/service.proto */
  rpc intri-dhcpserver-UpdateV4MACBased {
    input  {
      uses Pool;
    }
  }
  /* core/dhcpserver/service.proto */
  rpc intri-dhcpserver-GetV4PortBased {
    output  {
      uses Pool;
    }
  }
  /* core/dhcpserver/service.proto */
  rpc intri-dhcpserver-UpdateV4PortBased {
    input  {
      uses Pool;
    }
  }

}
