module sercom-stormcontrol {

  namespace "sercom:sercom-stormcontrol";
  prefix "sercom-stormcontrol";
  organization "
    Sercomm Inc.";
  contact "
    sercomm@sercomm.com.tw";
  revision 2022-06-24 {
    description "Build date.";
  }

  import sercom-device {
    prefix sercom-device;
  }
  import sercom-empty {
    prefix sercom-empty;
  }
  import sercom-common {
    prefix sercom-common;
  }
  typedef StormControlActionTypeOptions {
    type enumeration {
      enum STORM_CONTROL_ACTION_TYPE_SHUTDOWN {
        description "[Shutdown] the port interface will be shutdown when the percent of the outputed packet is over the max level";
        value 0;
      }
      enum STORM_CONTROL_ACTION_TYPE_BLOCKING {
        description "[Blocking] the port interface will be blocking when the percent of the outputed packet is over the max level";
        value 1;
      }
    }
  }
  typedef StormControlSuppressionTypeOptions {
    type enumeration {
      enum STORM_CONTROL_SUPPRESSION_TYPE_BROADCAST {
        description "[Broadcast] counter forwards broadcast bits/packets per second of lading as the standard";
        value 0;
      }
      enum STORM_CONTROL_SUPPRESSION_TYPE_MULTICAST {
        description "[Multicast] counter forwards multicast bits/packets per second of lading as the standard";
        value 1;
      }
      enum STORM_CONTROL_SUPPRESSION_TYPE_UNKNOWN_UNICAST {
        description "[Unknown Unicast] counter forwards unknown unicast bits/packets per second of lading as the standard";
        value 2;
      }
    }
  }
  typedef StormControlSuppressionUnitTypeOptions {
    type enumeration {
      enum STORM_CONTROL_SUPPRESSION_TYPE_BITS_PER_SECOND {
        description "[bits/sec.] counter bits per secound";
        value 0;
      }
      enum STORM_CONTROL_SUPPRESSION_TYPE_PACKETS_PER_SECOND {
        description "[packets/sec.] counter packets per secound";
        value 1;
      }
    }
  }
  grouping SuppressionConfigEntry {
    leaf SuppressionOption {
      mandatory "true";
      type StormControlSuppressionTypeOptions;
    }
    leaf IsEnable {
      mandatory "true";
      type boolean;
    }
    leaf ActionOption {
      mandatory "true";
      type StormControlActionTypeOptions;
    }
    leaf UnitOption {
      mandatory "true";
      type StormControlSuppressionUnitTypeOptions;
    }
    leaf BpsUpperThreshold {
      mandatory "true";
      type uint64;
    }
    leaf PpsUpperThreshold {
      mandatory "true";
      type uint64;
    }
  }
  grouping PortConfigEntry {
    container IdentifyNo {
      uses sercom-device:InterfaceIdentify;
    }
    leaf IsEnable {
      mandatory "true";
      type boolean;
    }
    container SuppressionList {
      list SuppressionList_Entry {
        uses SuppressionConfigEntry;
      }
    }
  }
  grouping PortConfig {
    container List {
      list List_Entry {
        uses PortConfigEntry;
      }
    }
  }
  grouping Config {
    leaf IsEnable {
      mandatory "true";
      type boolean;
    }
    container PortConfig {
      uses PortConfig;
    }
  }
  rpc sercom-stormcontrol-StormControl-GetConfig {
    output {
      uses Config;
    }
  }
  rpc sercom-stormcontrol-StormControl-SetEnabled {
    input {
      uses sercom-common:Enabled;
    }
  }
  rpc sercom-stormcontrol-StormControl-GetEnabled {
    output {
      uses sercom-common:Enabled;
    }
  }
  rpc sercom-stormcontrol-StormControl-GetPortConfig {
    output {
      uses PortConfig;
    }
  }
  rpc sercom-stormcontrol-StormControl-UpdatePortConfigEntry {
    input {
      uses PortConfigEntry;
    }
  }
  rpc sercom-stormcontrol-StormControl-UpdatePortConfig {
    input {
      uses PortConfig;
    }
  }
}
