module intri-port {
  namespace "intri:intri-port";
  prefix "intri-port";
  import stppb {
    prefix "stppb";
  }
  import portpb {
    prefix "portpb";
  }
  import devicepb {
    prefix "devicepb";
  }
  import eventpb {
    prefix "eventpb";
  }
  organization "Intrising Inc.";
  contact "xxx@intrising.com.tw";
  revision 2022-06-14 {
    description "Build date.";
  }
}
