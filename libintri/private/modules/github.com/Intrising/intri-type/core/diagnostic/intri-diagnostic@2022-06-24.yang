module intri-diagnostic {

  namespace "intri:intri-diagnostic";
  prefix "intri-diagnostic";
  organization "
    Intrising Inc.";
  contact "
    intrising@intrising.com.tw";
  revision 2022-06-24 {
    description "Build date.";
  }

  import intri-common {
    prefix intri-common;
  }
  import intri-empty {
    prefix intri-empty;
  }
  grouping ARPEntry {
    leaf IPAddr {
      mandatory "true";
      type string;
    }
    leaf MACAddr {
      mandatory "true";
      type string;
    }
  }
  grouping ARPTables {
    container List {
      list List_Entry {
        uses ARPEntry;
      }
    }
  }
  rpc intri-diagnostic-Diagnostic-RunPingTest {
    input {
      uses intri-common:IPAddress;
    }
    output {
      uses intri-common:Reply;
    }
  }
  rpc intri-diagnostic-Diagnostic-RunTraceRoute {
    input {
      uses intri-common:IPAddress;
    }
    output {
      uses intri-common:Reply;
    }
  }
  rpc intri-diagnostic-Diagnostic-RunDNSLookup {
    input {
      uses intri-common:Name;
    }
    output {
      uses intri-common:Reply;
    }
  }
  rpc intri-diagnostic-Diagnostic-GetARPTable {
    output {
      uses ARPTables;
    }
  }
}
