module with-defaults {

    namespace "TBD-by-IANA-with-defaults";
    prefix "wd";

    import netconf {
        prefix nc;
    }

    organization
        "Network Configuration Working Group";

    contact
     "WG Web:   <http://tools.ietf.org/wg/netconf/>
      WG List:  <mailto:netconf@ietf.org>

      WG Chair: Bert Wijnen
                <mailto:bertietf@bwijnen.net>

      WG Chair: Mehmet Ersue
                <mailto:mehmet.ersue@nsn.com>

      Editor:   Andy Bierman
                <mailto:andy@netconfcentral.com>

      Editor:   Balazs Lengyel
                <mailto:balazs.lengyel@ericsson.com>";

    description
        "YANG version of with-defaults data model.";

    revision 2009-02-24 {
        description "Initial version.";
    }

    typedef DefaultStyle {
        description
           "Selects the type of filtering behavior the agent will
            advertise in the 'with-defaults' capability.  The agent
            will use this default handling behavior if the 
            'with-defaults' parameter is not explicitly set.";
        type enumeration {
            enum report-all {
               description
                 "All default data is always reported.";
               value 1;
            }
            enum trim {
               description
                 "Values are not reported if they match the default.";
               value 2;
            }
            enum explicit {
               description
                 "Report values if they are explicitly set.";
               value 3;
            }
        }
    }

    grouping WithDefaults {
       leaf with-defaults {
         description 
           "With default agent behavior:
             - false: default data SHOULD NOT be returned.
             -  true: all default data MUST be returned.
            If not present, then the 'with-defaults' behavior
            is implementation-dependent.";
          type boolean;
       }
    }

    augment "/nc:get/nc:input" {
      uses WithDefaults;
    }

    augment "/nc:get-config/nc:input" {
      uses WithDefaults;
    }

    augment "/nc:copy-config/nc:input" {
      uses WithDefaults;
    }

}
