// Code generated by protoc-gen-yang. DO NOT EDIT.


/* ****************************************************************************************************
 * Import Path : "github.com/Intrising/intri-type/core/udld"                                          *
 * Dir Path    : github.com/Intrising/intri-type/core/udld                                            *
 * Go Package  : udld                                                                                 *
 * Files       : 2                                                                                    *
 **************************************************************************************************** */
module intri-udld {

  namespace "intri:intri-udld";

  prefix "intri-udld";

  organization "Intrising Inc.";

  contact "intrising@intrising.com.tw";

  revision 2022-06-23 {
    description "Build date.";
  }

  import intri-device {
    prefix intri-device;
  }
  import intri-empty {
    prefix intri-empty;
  }


  /* **************************************************************************************************
   * Enums       : 4                                                                                  *
   ************************************************************************************************** */
  /* core/udld/udld.proto */
  typedef ModeTypeOptions {
    type enumeration {
      enum MODE_TYPE_NORMAL {
        description "[Normal] UDLD detects the unidirectional link, the state will change to `undetermined` and send event.";
        value 0;
      }
      enum MODE_TYPE_AGGRESSIVE {
        description "[Aggressive] UDLD detects the unidirectional link, and sends the `UDLD probe message` for `N` seconds continually, if has no receives the `UDLD echo message`, the state will change to `err-disable` to drop all packets.";
        value 1;
      }
    }
  }
  /* core/udld/udld.proto */
  typedef PortStateTypeOptions {
    type enumeration {
      enum PORT_STATE_TYPE_NONE {
        description "[None] the UDLD is not enabled.";
        value 0;
      }
      enum PORT_STATE_TYPE_DETECTION {
        description "[Detection] the UDLD is detecting the link.";
        value 1;
      }
      enum PORT_STATE_TYPE_BIDIRECTIONALITY {
        description "[Bidirectionality] the UDLD detects bidirectional link.";
        value 2;
      }
      enum PORT_STATE_TYPE_UNDETERMINED {
        description "[Undetermined] the UDLD detects unidirectional link, will send event.";
        value 3;
      }
      enum PORT_STATE_TYPE_ERROR_DISABLED {
        description "[Error-Disabled] the UDLD detects unidirectional link, will drop all packet.";
        value 4;
      }
    }
  }
  /* core/udld/udld.proto */
  typedef PortFaultTypeOptions {
    type enumeration {
      enum PORT_FAULT_TYPE_NONE {
        description "[None] failed get state";
        value 0;
      }
      enum PORT_FAULT_TYPE_TX {
        description "[Tx] the port is tx only";
        value 1;
      }
      enum PORT_FAULT_TYPE_RX {
        description "[Rx] the port is rx only";
        value 2;
      }
      enum PORT_FAULT_TYPE_BOTH {
        description "[Both] the port is tx+rx";
        value 3;
      }
    }
  }
  /* core/udld/udld.proto */
  typedef PacketOpcodeTypeOptions {
    type enumeration {
      enum PACKET_OPCODE_TYPE_OPTIONS_RESERVED {
        description "[Reserved] Reserved, the hex is 0x00";
        value 0;
      }
      enum PACKET_OPCODE_TYPE_OPTIONS_PROBE {
        description "[Probe] Probe message, the hex is 0x01";
        value 1;
      }
      enum PACKET_OPCODE_TYPE_OPTIONS_ECHO {
        description "[Echo] Echo message, the hex is 0x02";
        value 2;
      }
      enum PACKET_OPCODE_TYPE_OPTIONS_FLUSH {
        description "[Flush] Flush message, the hex is 0x03";
        value 3;
      }
    }
  }


  /* **************************************************************************************************
   * Msgs        : 14                                                                                 *
   ************************************************************************************************** */
  /* core/udld/udld.proto */
  grouping Config {
    container BasicConfig {
      uses BasicConfig;
    }
    container PortConfig {
      uses PortConfig;
    }
  }
  /* core/udld/udld.proto */
  grouping BasicConfig {
    leaf IsEnabled {
      type boolean;
    }
    leaf ModeOption {
      type ModeTypeOptions;
    }
    leaf MessageIntervalSeconds {
      type int32;
    }
  }
  /* core/udld/udld.proto */
  grouping PortConfig {
    container List {
      list List_Entry {
        uses PortConfigEntry;
      }
    }
  }
  /* core/udld/udld.proto */
  grouping PortConfigEntry {
    container IdentifyNo {
      uses intri-device:InterfaceIdentify;
    }
    leaf IsEnabled {
      type boolean;
    }
    leaf ModeOption {
      type ModeTypeOptions;
    }
  }
  /* core/udld/udld.proto */
  grouping Status {
    container PortStatus {
      uses PortStatus;
    }
    container NeighborStatus {
      uses NeighborStatus;
    }
  }
  /* core/udld/udld.proto */
  grouping PortStatus {
    container List {
      list List_Entry {
        uses PortStatusEntry;
      }
    }
  }
  /* core/udld/udld.proto */
  grouping PortStatusEntry {
    container IdentifyNo {
      uses intri-device:InterfaceIdentify;
    }
    leaf IsEnabled {
      type boolean;
    }
    leaf PortLinkUp {
      type boolean;
    }
    leaf FaultOption {
      type PortFaultTypeOptions;
    }
    leaf StateOption {
      type PortStateTypeOptions;
    }
    leaf ModeOption {
      type ModeTypeOptions;
    }
  }
  /* core/udld/udld.proto */
  grouping NeighborStatus {
    container List {
      list List_Entry {
        uses NeighborStatusEntry;
      }
    }
  }
  /* core/udld/udld.proto */
  grouping NeighborStatusEntry {
    container IdentifyNo {
      uses intri-device:InterfaceIdentify;
    }
    leaf DeviceID {
      type string;
    }
    leaf PortID {
      type string;
    }
    leaf MacAddress {
      type string;
    }
    leaf DeviceName {
      type string;
    }
    leaf StateOption {
      type PortStateTypeOptions;
    }
    leaf ExpirationTimeSeconds {
      type int32;
    }
    leaf MessageTimeSeconds {
      type int32;
    }
  }
  /* core/udld/udld.proto */
  grouping Statistics {
    container Total {
      uses PacketStatistics;
    }
    container Port {
      uses PortStatistics;
    }
  }
  /* core/udld/udld.proto */
  grouping PortStatistics {
    container List {
      list List_Entry {
        uses PortStatisticsEntry;
      }
    }
  }
  /* core/udld/udld.proto */
  grouping PortStatisticsEntry {
    container IdentifyNo {
      uses intri-device:InterfaceIdentify;
    }
    container Statistics {
      uses PacketStatistics;
    }
  }
  /* core/udld/udld.proto */
  grouping PacketStatistics {
    container List {
      list List_Entry {
        uses PacketStatisticsEntry;
      }
    }
  }
  /* core/udld/udld.proto */
  grouping PacketStatisticsEntry {
    leaf OpcodeOption {
      type PacketOpcodeTypeOptions;
    }
    leaf Count {
      type uint64;
    }
  }


  /* **************************************************************************************************
   * Services    : 1                                                                                  *
   ************************************************************************************************** */

  /* **************************************************************************************************
   * Service     : UDLD                                                                               *
   * Methods     : 10                                                                                 *
   ************************************************************************************************** */
  /* core/udld/service.proto */
  rpc intri-udld-GetStatus {
    output  {
      uses Status;
    }
  }
  /* core/udld/service.proto */
  rpc intri-udld-RunRestorePortStatus {
    input  {
      uses intri-device:PortList;
    }
  }
  /* core/udld/service.proto */
  rpc intri-udld-GetConfig {
    output  {
      uses Config;
    }
  }
  /* core/udld/service.proto */
  rpc intri-udld-GetBasicConfig {
    output  {
      uses BasicConfig;
    }
  }
  /* core/udld/service.proto */
  rpc intri-udld-UpdateBasicConfig {
    input  {
      uses BasicConfig;
    }
  }
  /* core/udld/service.proto */
  rpc intri-udld-GetPortConfig {
    output  {
      uses PortConfig;
    }
  }
  /* core/udld/service.proto */
  rpc intri-udld-UpdatePortConfig {
    input  {
      uses PortConfig;
    }
  }
  /* core/udld/service.proto */
  rpc intri-udld-UpdatePortConfigEntry {
    input  {
      uses PortConfigEntry;
    }
  }
  /* core/udld/service.proto */
  rpc intri-udld-GetStatistics {
    output  {
      uses Statistics;
    }
  }
  /* core/udld/service.proto */
  rpc intri-udld-RunClearStatistics {
    input  {
      uses intri-device:PortList;
    }
  }

}
