// Code generated by protoc-gen-yang. DO NOT EDIT.


/* ****************************************************************************************************
 * Import Path : "github.com/Intrising/intri-type/device"                                             *
 * Dir Path    : github.com/Intrising/intri-type/device                                               *
 * Go Package  : device                                                                               *
 * Files       : 8                                                                                    *
 **************************************************************************************************** */
module intri-device {

  namespace "intri:intri-device";

  prefix "intri-device";

  organization "Intrising Inc.";

  contact "intrising@intrising.com.tw";

  revision 2022-06-23 {
    description "Build date.";
  }

  import intri-empty {
    prefix intri-empty;
  }
  import intri-common {
    prefix intri-common;
  }


  /* **************************************************************************************************
   * Enums       : 18                                                                                 *
   ************************************************************************************************** */
  /* device/board.proto */
  typedef RCLKTypeOptions {
    type enumeration {
      enum RCLK_TYPE_0 {
        description "[RCLK 0] RCLK 0";
        value 0;
      }
      enum RCLK_TYPE_1 {
        description "[RCLK 1] RCLK 1";
        value 1;
      }
    }
  }
  /* device/board.proto */
  typedef InputClockIndexTypeOptions {
    type enumeration {
      enum INPUT_CLOCK_INDEX_TYPE_0 {
        description "[Clock Index 0] Clock Index 0";
        value 0;
      }
      enum INPUT_CLOCK_INDEX_TYPE_1 {
        description "[Clock Index 1] Clock Index 1";
        value 1;
      }
      enum INPUT_CLOCK_INDEX_TYPE_2 {
        description "[Clock Index 2] Clock Index 2";
        value 2;
      }
      enum INPUT_CLOCK_INDEX_TYPE_3 {
        description "[Clock Index 3] Clock Index 3";
        value 3;
      }
      enum INPUT_CLOCK_INDEX_TYPE_4 {
        description "[Clock Index 4] Clock Index 4";
        value 4;
      }
      enum INPUT_CLOCK_INDEX_TYPE_5 {
        description "[Clock Index 5] Clock Index 5";
        value 5;
      }
      enum INPUT_CLOCK_INDEX_TYPE_6 {
        description "[Clock Index 6] Clock Index 6";
        value 6;
      }
      enum INPUT_CLOCK_INDEX_TYPE_7 {
        description "[Clock Index 7] Clock Index 7";
        value 7;
      }
      enum INPUT_CLOCK_INDEX_TYPE_8 {
        description "[Clock Index 8] Clock Index 8";
        value 8;
      }
      enum INPUT_CLOCK_INDEX_TYPE_9 {
        description "[Clock Index 9] Clock Index 9";
        value 9;
      }
      enum INPUT_CLOCK_INDEX_TYPE_10 {
        description "[Clock Index 10] Clock Index 10";
        value 10;
      }
      enum INPUT_CLOCK_INDEX_TYPE_11 {
        description "[Clock Index 11] Clock Index 11";
        value 11;
      }
      enum INPUT_CLOCK_INDEX_TYPE_12 {
        description "[Clock Index 12] Clock Index 12";
        value 12;
      }
      enum INPUT_CLOCK_INDEX_TYPE_13 {
        description "[Clock Index 13] Clock Index 13";
        value 13;
      }
      enum INPUT_CLOCK_INDEX_TYPE_14 {
        description "[Clock Index 14] Clock Index 14";
        value 14;
      }
      enum INPUT_CLOCK_INDEX_TYPE_15 {
        description "[Clock Index 15] Clock Index 15";
        value 15;
      }
    }
  }
  /* device/board.proto */
  typedef InputClockTypeOptions {
    type enumeration {
      enum INPUT_CLOCK_TYPE_MAC_CLOCK_0 {
        description "[MAC Clock 0] MAC Clock 0";
        value 0;
      }
      enum INPUT_CLOCK_TYPE_MAC_CLOCK_1 {
        description "[MAC Clock 1] MAC Clock 1";
        value 1;
      }
      enum INPUT_CLOCK_TYPE_PHY_A_CLOCK_0 {
        description "[PHY A Clock 0] PHY A Clock 0";
        value 2;
      }
      enum INPUT_CLOCK_TYPE_PHY_A_CLOCK_1 {
        description "[PHY A Clock 1] PHY A Clock 1";
        value 3;
      }
      enum INPUT_CLOCK_TYPE_PHY_B_CLOCK_0 {
        description "[PHY B Clock 0] PHY B Clock 0";
        value 4;
      }
      enum INPUT_CLOCK_TYPE_PHY_B_CLOCK_1 {
        description "[PHY B Clock 1] PHY B Clock 1";
        value 5;
      }
      enum INPUT_CLOCK_TYPE_PHY_C_CLOCK_0 {
        description "[PHY C Clock 0] PHY C Clock 0";
        value 6;
      }
      enum INPUT_CLOCK_TYPE_PHY_C_CLOCK_1 {
        description "[PHY C Clock 1] PHY C Clock 1";
        value 7;
      }
      enum INPUT_CLOCK_TYPE_BITS_IN {
        description "[Bits In] Bits In";
        value 8;
      }
      enum INPUT_CLOCK_TYPE_1PPS_GPS {
        description "[1pps GPS] 1pps GPS";
        value 10;
      }
      enum INPUT_CLOCK_TYPE_1PPS_IN {
        description "[1pps In] 1pps In";
        value 11;
      }
      enum INPUT_CLOCK_TYPE_10MHZ_IN {
        description "[10Mhz In] 10Mhz In";
        value 12;
      }
      enum INPUT_CLOCK_TYPE_1PPS_FEEDBACK {
        description "[1pps Feedback] 1pps Feedback";
        value 13;
      }
    }
  }
  /* device/board.proto */
  typedef LedTypeOptions {
    type enumeration {
      enum LED_TYPE_OFF {
        description "[Off]";
        value 0;
      }
      enum LED_TYPE_ON {
        description "[On]";
        value 1;
      }
      enum LED_TYPE_ORANGE {
        description "[Orange]";
        value 2;
      }
      enum LED_TYPE_GREEN {
        description "[Green]";
        value 3;
      }
    }
  }
  /* device/board.proto */
  typedef PhyInterfaceTypeOptions {
    type enumeration {
      enum PHY_INTERFACE_TYPE_SMI {
        description "[Smi]";
        value 0;
      }
      enum PHY_INTERFACE_TYPE_XSMI {
        description "[Xsmi]";
        value 1;
      }
      enum PHY_INTERFACE_TYPE_UNUSED {
        description "[Unused]";
        value 2;
      }
    }
  }
  /* device/board.proto */
  typedef FactoryHwFeatureTypeOptions {
    type enumeration {
      enum FACTORY_HW_FEATURE_TYPE_POE_PLUS_PLUS {
        description "[PoE++] Power over Ethernet plus (30W ports) supported";
        value 0;
      }
      enum FACTORY_HW_FEATURE_TYPE_POE_PLUS {
        description "[PoE+] Power over Ethernet plus (30W ports) supported";
        value 1;
      }
      enum FACTORY_HW_FEATURE_TYPE_EEE {
        description "[EEE] Energy Efficient Ethernet";
        value 2;
      }
      enum FACTORY_HW_FEATURE_TYPE_RTC {
        description "[RTC] Local real time clock";
        value 3;
      }
      enum FACTORY_HW_FEATURE_TYPE_SFP {
        description "[SFP] Pluggable optical port";
        value 4;
      }
    }
  }
  /* device/board.proto */
  typedef PortPropertyTypeOptions {
    type enumeration {
      enum PORT_PROPERTIES_TYPE_10M_FULL {
        description "[10M FULL] This port is capable of running at 10Mbit/s";
        value 0;
      }
      enum PORT_PROPERTIES_TYPE_10M_HALF {
        description "[10M HALF] This port is capable of running at 10Mbit/s";
        value 1;
      }
      enum PORT_PROPERTIES_TYPE_100M_FULL {
        description "[100M FULL] This port is capable of running at 100Mbit/s";
        value 2;
      }
      enum PORT_PROPERTIES_TYPE_100M_HALF {
        description "[100M HALF] This port is capable of running at 100Mbit/s";
        value 3;
      }
      enum PORT_PROPERTIES_TYPE_1000M_FULL {
        description "[1G FULL] This port is capable of running at 1000Mbit/s";
        value 4;
      }
      enum PORT_PROPERTIES_TYPE_2500M_FULL {
        description "[2.5G FULL] This port is capable of running at 2500Mbit/s";
        value 5;
      }
      enum PORT_PROPERTIES_TYPE_5G_FULL {
        description "[5G FULL] This port is capable of running at 5Gbit/s";
        value 6;
      }
      enum PORT_PROPERTIES_TYPE_10G_FULL {
        description "[10G FULL] This port is capable of running at 10Gbit/s";
        value 7;
      }
      enum PORT_PROPERTIES_TYPE_25G_FULL {
        description "[25G FULL] This port is capable of running at 25Gbit/s";
        value 8;
      }
      enum PORT_PROPERTIES_TYPE_RJ45 {
        description "[RJ45] This port uses as RJ45 connector";
        value 9;
      }
      enum PORT_PROPERTIES_TYPE_SFP {
        description "[SFP] This port uses a pluggable SFP";
        value 10;
      }
      enum PORT_PROPERTIES_TYPE_POE {
        description "[PoE] This port is capable to supply Power over Ethernet (PoE)";
        value 11;
      }
      enum PORT_PROPERTIES_TYPE_POE_PLUS {
        description "[PoE+] This port is capable to supply Power over Ethernet Extended (PoE+)";
        value 12;
      }
      enum PORT_PROPERTIES_TYPE_POE_PLUS_PLUS {
        description "[PoE++] This port is capable to supply Power over Ethernet Extended (PoE+)";
        value 13;
      }
      enum PORT_PROPERTIES_TYPE_LINK_PORT {
        description "[Link Port] This port is capable to supply Power over Ethernet Extended (PoE+)";
        value 14;
      }
    }
  }
  /* device/board.proto */
  typedef DevicePortSpeedDuplexTypeOptions {
    type enumeration {
      enum DEVICE_PORT_SPEED_DUPLEX_TYPE_AUTO {
        description "[Auto]";
        value 0;
      }
      enum DEVICE_PORT_SPEED_DUPLEX_TYPE_10M_FULL {
        description "[10 Mbps / Full]";
        value 1;
      }
      enum DEVICE_PORT_SPEED_DUPLEX_TYPE_10M_HALF {
        description "[10 Mbps / Half]";
        value 2;
      }
      enum DEVICE_PORT_SPEED_DUPLEX_TYPE_100M_FULL {
        description "[100 Mbps / Full]";
        value 3;
      }
      enum DEVICE_PORT_SPEED_DUPLEX_TYPE_100M_HALF {
        description "[100 Mbps / Half]";
        value 4;
      }
      enum DEVICE_PORT_SPEED_DUPLEX_TYPE_1000M_FULL {
        description "[1 Gbps  / Full]";
        value 5;
      }
      enum DEVICE_PORT_SPEED_DUPLEX_TYPE_2500M_FULL {
        description "[2.5 Gbps / Full]";
        value 6;
      }
      enum DEVICE_PORT_SPEED_DUPLEX_TYPE_5G_FULL {
        description "[5 Gbps / Full]";
        value 7;
      }
      enum DEVICE_PORT_SPEED_DUPLEX_TYPE_10G_FULL {
        description "[10 Gbps / Full]";
        value 8;
      }
      enum DEVICE_PORT_SPEED_DUPLEX_TYPE_25G_FULL {
        description "[25 Gbps / Full]";
        value 9;
      }
      enum DEVICE_PORT_SPEED_DUPLEX_TYPE_40G_FULL {
        description "[40 Gbps / Full]";
        value 10;
      }
      enum DEVICE_PORT_SPEED_DUPLEX_TYPE_100G_FULL {
        description "[100 Gbps / Full]";
        value 11;
      }
      enum DEVICE_PORT_SPEED_DUPLEX_TYPE_NA {
        description "[NA]";
        value 12;
      }
    }
  }
  /* device/board.proto */
  typedef PortInterfaceTypeOptions {
    type enumeration {
      enum PORT_INTERFACE_TYPE_COPPER {
        description "[Copper] Normal copper interface";
        value 0;
      }
      enum PORT_INTERFACE_TYPE_OPTICAL {
        description "[Optical] Optical interface";
        value 1;
      }
    }
  }
  /* device/board.proto */
  typedef DeviceTypeOptions {
    type enumeration {
      enum DEVICE_TYPE_MCU {
        description "[MCU] MCU";
        value 0;
      }
      enum DEVICE_TYPE_I2C {
        description "[I2C] I2C";
        value 1;
      }
      enum DEVICE_TYPE_GPIO {
        description "[GPIO] GPIO";
        value 2;
      }
    }
  }
  /* device/board.proto */
  typedef MonitorTypeOptions {
    type enumeration {
      enum MONITOR_TYPE_TEMP_OK {
        description "[Temperature Normal] Temperature Normal";
        value 0;
      }
      enum MONITOR_TYPE_TEMP_WARN {
        description "[Temperature Warning] Temperature Warning";
        value 1;
      }
      enum MONITOR_TYPE_FAN_OK {
        description "[Fan Speed Ok] Fan Speed Ok";
        value 2;
      }
      enum MONITOR_TYPE_FAN_WARN {
        description "[Fan Speed Warn] Fan Speed Warn";
        value 3;
      }
    }
  }
  /* device/board.proto */
  typedef PSUTypeOptions {
    type enumeration {
      enum PSU_TYPE_LOCATION_OK {
        description "[Location Ok] Location Ok";
        value 0;
      }
      enum PSU_TYPE_LOCATION_WARN {
        description "[Location Warn] Location Warn";
        value 1;
      }
      enum PSU_TYPE_AC_OK {
        description "[AC Ok] AC Ok";
        value 2;
      }
      enum PSU_TYPE_AC_WARN {
        description "[AC Warning] AC Warning";
        value 3;
      }
      enum PSU_TYPE_PW_OK {
        description "[Power Ok] Power Ok";
        value 4;
      }
      enum PSU_TYPE_PW_WARN {
        description "[Power Warning] Power Warning";
        value 5;
      }
      enum PSU_TYPE_FAIL {
        description "[PSU Failed] Failed";
        value 6;
      }
    }
  }
  /* device/board.proto */
  typedef FanTypeOptions {
    type enumeration {
      enum FAN_TYPE_RPM {
        description "[RPM] RPM";
        value 0;
      }
    }
  }
  /* device/board.proto */
  typedef FanDeviceTypeOptions {
    type enumeration {
      enum FAN_DEVICE_TYPE_RPM {
        description "[RPM] RPM";
        value 0;
      }
    }
  }
  /* device/board.proto */
  typedef PoEDeviceTypeOptions {
    type enumeration {
      enum POE_DEVICE_TYPE_I2C {
        description "[I2C] I2C";
        value 0;
      }
      enum POE_DEVICE_TYPE_UART {
        description "[UART] UART";
        value 1;
      }
    }
  }
  /* device/boundary.proto */
  typedef BoundaryTypeOptions {
    type enumeration {
      enum BOUNDARY_TYPE_INT {
        description "[Int]";
        value 0;
      }
      enum BOUNDARY_TYPE_DOUBLE {
        description "[Double]";
        value 1;
      }
    }
  }
  /* device/device.proto */
  typedef LayerTypeOptions {
    type enumeration {
      enum LAYER_TYPE_L2 {
        description "[L2]";
        value 0;
      }
      enum LAYER_TYPE_L3 {
        description "[L3]";
        value 1;
      }
    }
  }
  /* device/device.proto */
  typedef InterfaceTypeOptions {
    type enumeration {
      enum INTERFACE_TYPE_VLAN {
        description "[VLAN]";
        value 0;
      }
      enum INTERFACE_TYPE_PORT {
        description "[Port]";
        value 1;
      }
      enum INTERFACE_TYPE_TRUNK {
        description "[LAG]";
        value 2;
      }
      enum INTERFACE_TYPE_MULTICAST {
        description "[Multicast]";
        value 3;
      }
    }
  }


  /* **************************************************************************************************
   * Msgs        : 51                                                                                 *
   ************************************************************************************************** */
  /* device/board.proto */
  grouping LedInfo {
    leaf Name {
      type string;
    }
    leaf PortNo {
      type int32;
    }
    leaf Type {
      type DeviceTypeOptions;
    }
    leaf Direction {
      type string;
    }
    choice Device {
      container LEDDevice {
        uses MCULedDevice;
      }
      container I2CDevice {
        uses I2CDevice;
      }
      container GPIODevice {
        uses GPIODevice;
      }
    }
  }
  /* device/board.proto */
  grouping MonitorInfo {
    leaf Name {
      type string;
    }
    leaf Type {
      type DeviceTypeOptions;
    }
    leaf Direction {
      type string;
    }
    choice Device {
      container MonitorDevice {
        uses MCUMonitorDevice;
      }
      container I2CDevice {
        uses I2CDevice;
      }
      container GPIODevice {
        uses GPIODevice;
      }
    }
  }
  /* device/board.proto */
  grouping PSUInfo {
    leaf Name {
      type string;
    }
    leaf Type {
      type DeviceTypeOptions;
    }
    leaf Direction {
      type string;
    }
    choice Device {
      container PSUDevice {
        uses MCUPSUDevice;
      }
      container I2CDevice {
        uses I2CDevice;
      }
      container GPIODevice {
        uses GPIODevice;
      }
    }
  }
  /* device/board.proto */
  grouping MCULedDevice {
    leaf I2CAddr {
      type int32;
    }
    leaf AddrRegister {
      type int32;
    }
    leaf LedAction {
      type LedTypeOptions;
    }
    leaf ActiveBit {
      type int32;
    }
  }
  /* device/board.proto */
  grouping MCUMonitorDevice {
    leaf I2CAddr {
      type int32;
    }
    leaf AddrRegister {
      type int32;
    }
    leaf MonitorAction {
      type MonitorTypeOptions;
    }
    leaf ActiveBit {
      type int32;
    }
  }
  /* device/board.proto */
  grouping MCUPSUDevice {
    leaf I2CAddr {
      type int32;
    }
    leaf AddrRegister {
      type int32;
    }
    leaf PSUAction {
      type PSUTypeOptions;
    }
    leaf ActiveBit {
      type int32;
    }
  }
  /* device/board.proto */
  grouping MCUFanDevice {
    leaf I2CAddr {
      type int32;
    }
    leaf AddrRegister {
      type int32;
    }
    leaf FANAction {
      type FanTypeOptions;
    }
    leaf ActiveBit {
      type int32;
    }
  }
  /* device/board.proto */
  grouping I2CDevice {
    leaf I2CAddr {
      type int32;
    }
    leaf AddrRegister {
      type int32;
    }
    leaf Action {
      type int32;
    }
    leaf ActiveBit {
      type int32;
    }
  }
  /* device/board.proto */
  grouping GPIODevice {
    leaf Register {
      type int32;
    }
    leaf Pin {
      type int32;
    }
    leaf Action {
      type boolean;
    }
    leaf Enable {
      type boolean;
    }
  }
  /* device/board.proto */
  grouping I2Cinfo {
    leaf Name {
      type string;
    }
    leaf Direction {
      type string;
    }
    container Device {
      uses I2CDevice;
    }
  }
  /* device/board.proto */
  grouping GPIOInfo {
    leaf Name {
      type string;
    }
    leaf Direction {
      type string;
    }
    container Device {
      uses GPIODevice;
    }
  }
  /* device/board.proto */
  grouping PTPClockSynchronizerInfo {
    leaf Name {
      type string;
    }
    leaf Direction {
      type string;
    }
    container Device {
      uses I2CDevice;
    }
  }
  /* device/board.proto */
  grouping GPSInfo {
    leaf Name {
      type string;
    }
    leaf Path {
      type string;
    }
    leaf Direction {
      type string;
    }
  }
  /* device/board.proto */
  grouping ToDInfo {
    leaf Name {
      type string;
    }
    leaf Path {
      type string;
    }
    leaf Direction {
      type string;
    }
  }
  /* device/board.proto */
  grouping UARTDevice {
    leaf Name {
      type string;
    }
    leaf Path {
      type string;
    }
    leaf Direction {
      type string;
    }
    leaf Bandwidth {
      type int32;
    }
  }
  /* device/board.proto */
  grouping FanInfo {
    leaf Name {
      type string;
    }
    leaf Type {
      type FanDeviceTypeOptions;
    }
    leaf FanNumber {
      type int32;
    }
    choice Device {
      container FANDevice {
        uses MCUFanDevice;
      }
      container I2CDevice {
        uses I2CDevice;
      }
      container GPIODevice {
        uses GPIODevice;
      }
    }
  }
  /* device/board.proto */
  grouping PoEInfo {
    leaf Name {
      type string;
    }
    leaf Type {
      type PoEDeviceTypeOptions;
    }
    choice Device {
      container I2CDevice {
        uses I2CDevice;
      }
      container UartDevice {
        uses UARTDevice;
      }
    }
  }
  /* device/board.proto */
  grouping HardwareInfo {
    container DeviceLed {
      list DeviceLed_Entry {
        uses LedInfo;
      }
    }
    container DeviceHWMonitor {
      list DeviceHWMonitor_Entry {
        uses MonitorInfo;
      }
    }
    container DevicePSU {
      list DevicePSU_Entry {
        uses PSUInfo;
      }
    }
    container DeviceI2C {
      list DeviceI2C_Entry {
        uses I2Cinfo;
      }
    }
    container DeviceHW {
      list DeviceHW_Entry {
        uses GPIOInfo;
      }
    }
    container DevicePTP {
      list DevicePTP_Entry {
        uses PTPClockSynchronizerInfo;
      }
    }
    container DeviceGPS {
      list DeviceGPS_Entry {
        uses GPSInfo;
      }
    }
    container DeviceToD {
      list DeviceToD_Entry {
        uses ToDInfo;
      }
    }
    container DeviceFan {
      list DeviceFan_Entry {
        uses FanInfo;
      }
    }
    container DevicePoE {
      list DevicePoE_Entry {
        uses PoEInfo;
      }
    }
  }
  /* device/board.proto */
  grouping HardwareTableSize {
    leaf TcamSize {
      type int32;
    }
    leaf BridgeFDBEntries {
      type int32;
    }
    leaf VirtualPorts {
      type int32;
    }
    leaf VirtualBridgeDomains {
      type int32;
    }
    leaf ARPTableEntries {
      type int32;
    }
    leaf RouterIPv4HostEntries {
      type int32;
    }
    leaf RouterIPv6HostEntries {
      type int32;
    }
    leaf RouterNextHopEntries {
      type int32;
    }
    leaf MulticastPhysicalPortGroups {
      type int32;
    }
    leaf MulticastLinkedListEntries {
      type int32;
    }
    leaf CentralizedCounters {
      type int32;
    }
    leaf SpanningTreeGroups {
      type int32;
    }
    leaf QoSProfiles {
      type int32;
    }
    leaf L2L3PortIsolation {
      type int32;
    }
  }
  /* device/board.proto */
  grouping PhyInterface {
    leaf Interface {
      type int32;
    }
    leaf Type {
      type PhyInterfaceTypeOptions;
    }
  }
  /* device/board.proto */
  grouping PortInfo {
    leaf PortNo {
      type int32;
    }
    leaf MACChip {
      type int32;
    }
    leaf MACNo {
      type int32;
    }
    leaf PortGroup {
      type int32;
    }
    leaf PhyID1 {
      type int32;
    }
    leaf PhyID2 {
      type int32;
    }
    container PhyInterface {
      uses PhyInterface;
    }
    leaf PoENo {
      type int32;
    }
    container PoEChannel {
      leaf-list PoEChannel_Entry {
        type int32;
      }
    }
    leaf PoEChipNo {
      type int32;
    }
    leaf MacsecEncLen {
      type int32;
    }
    leaf InterfaceType {
      type PortInterfaceTypeOptions;
    }
    container Properties {
      leaf-list Properties_Entry {
        type PortPropertyTypeOptions;
      }
    }
    leaf DeviceID {
      type int32;
    }
    container SpeedProperties {
      leaf-list SpeedProperties_Entry {
        type DevicePortSpeedDuplexTypeOptions;
      }
    }
  }
  /* device/board.proto */
  grouping BoardInfo {
    leaf SystemDescription {
      type string;
    }
    container PortLists {
      list PortLists_Entry {
        uses PortInfo;
      }
    }
    container HwFeatures {
      leaf-list HwFeatures_Entry {
        type FactoryHwFeatureTypeOptions;
      }
    }
    container HwSize {
      uses HardwareTableSize;
    }
    leaf CPUPort {
      type int32;
    }
    container BoardDevice {
      uses HardwareInfo;
    }
    container TimeControl {
      uses TimeControlInfo;
    }
    leaf EnterpriseOID {
      type string;
    }
  }
  /* device/board.proto */
  grouping TimeControlSpeedFrequencyEntry {
    leaf Speed {
      type PortPropertyTypeOptions;
    }
    leaf Frequency {
      type int64;
    }
    leaf M {
      type int64;
    }
    leaf N {
      type int64;
    }
    leaf Div {
      type int64;
    }
  }
  /* device/board.proto */
  grouping TimeControlPortInfoEntry {
    leaf PortNo {
      type int32;
    }
    leaf RCLKPin {
      type RCLKTypeOptions;
    }
    leaf Frequency {
      type int64;
    }
    leaf InputClock {
      type InputClockIndexTypeOptions;
    }
  }
  /* device/board.proto */
  grouping TimeControlInfo {
    container InputClockMapping {
      list InputClockMapping_Entry {
        key "Key";
        unique "Key";
        leaf Key {
          type string;
        }
        leaf Value {
          type InputClockIndexTypeOptions;
        }
      }
    }
    container PortInfoList {
      list PortInfoList_Entry {
        uses TimeControlPortInfoEntry;
      }
    }
    container SpeedFrequencyList {
      list SpeedFrequencyList_Entry {
        uses TimeControlSpeedFrequencyEntry;
      }
    }
  }
  /* device/boundary.proto */
  grouping Boundary {
    leaf Type {
      type BoundaryTypeOptions;
    }
    leaf Max {
      type int32;
    }
    leaf Min {
      type int32;
    }
    leaf Lower {
      type decimal64 {
        fraction-digits 2;
      }
    }
    leaf Upper {
      type decimal64 {
        fraction-digits 2;
      }
    }
  }
  /* device/boundary.proto */
  grouping BoundaryAll {
    container VLAN {
      uses BoundaryVLAN;
    }
    container Access {
      uses BoundaryAccess;
    }
    container DDM {
      uses BoundaryDDM;
    }
    container ACL {
      uses BoundaryACL;
    }
    container Log {
      uses BoundaryLog;
    }
    container Mirroring {
      uses BoundaryMirroring;
    }
    container Trunk {
      uses BoundaryTRUNK;
    }
    container FDB {
      uses BoundaryFDB;
    }
    container QoS {
      uses BoundaryQoS;
    }
    container Multicast {
      uses BoundaryMulticast;
    }
    container PoE {
      uses BoundaryPoE;
    }
    container Files {
      uses BoundaryFiles;
    }
    container TimeRange {
      uses BoundaryTimeRange;
    }
    container DHCPServer {
      uses BoundaryDHCPServer;
    }
    container Monitor {
      uses BoundaryMonitor;
    }
  }
  /* device/boundary.proto */
  grouping BoundaryDHCPServer {
    container MACBased {
      uses Boundary;
    }
  }
  /* device/boundary.proto */
  grouping BoundaryVLAN {
    container VlanID {
      uses Boundary;
    }
    container VlanFilter {
      uses Boundary;
    }
    container ProtocolBased {
      uses Boundary;
    }
    container MACBased {
      uses Boundary;
    }
    container SubnetBased {
      uses Boundary;
    }
    container TPIDsRange {
      uses Boundary;
    }
    container ProtocolClasses {
      uses Boundary;
    }
    container SelectiveQinQ {
      uses Boundary;
    }
    container Mapping {
      uses Boundary;
    }
  }
  /* device/boundary.proto */
  grouping BoundaryDDM {
    container DdmTemperature {
      uses Boundary;
    }
    container DdmVoltage {
      uses Boundary;
    }
    container DdmTxBias {
      uses Boundary;
    }
    container DdmRxPower {
      uses Boundary;
    }
    container DdmTxPower {
      uses Boundary;
    }
  }
  /* device/boundary.proto */
  grouping BoundaryACL {
    container ACLs {
      uses Boundary;
    }
    container ACEs {
      uses Boundary;
    }
    container Binding {
      uses Boundary;
    }
    container Flow {
      uses Boundary;
    }
    container FlowRules {
      uses Boundary;
    }
    container Rules {
      uses Boundary;
    }
  }
  /* device/boundary.proto */
  grouping BoundaryLog {
    container LogRotateSize {
      uses Boundary;
    }
    container LogRotateFileCount {
      uses Boundary;
    }
    container LogTargetList {
      uses Boundary;
    }
  }
  /* device/boundary.proto */
  grouping BoundaryAccess {
    container Users {
      uses Boundary;
    }
    container UsersAssociatedGroups {
      uses Boundary;
    }
    container Groups {
      uses Boundary;
    }
    container GroupsPattern {
      uses Boundary;
    }
    container Restrictions {
      uses Boundary;
    }
    container Servers {
      uses Boundary;
    }
  }
  /* device/boundary.proto */
  grouping BoundaryMirroring {
    container Session {
      uses Boundary;
    }
  }
  /* device/boundary.proto */
  grouping BoundaryFDB {
    container FDBSize {
      uses Boundary;
    }
    container AgeTime {
      uses Boundary;
    }
    container PortLearningLimit {
      uses Boundary;
    }
    container PortSecurityLearningLimit {
      uses Boundary;
    }
    container ForwardLimit {
      uses Boundary;
    }
    container DropLimit {
      uses Boundary;
    }
  }
  /* device/boundary.proto */
  grouping BoundaryTRUNK {
    container IDRange {
      uses Boundary;
    }
    container PriorityRange {
      uses Boundary;
    }
    container MemberRange {
      uses Boundary;
    }
  }
  /* device/boundary.proto */
  grouping BoundaryMulticast {
    container VIDXRange {
      uses Boundary;
    }
    container StaticEntries {
      uses Boundary;
    }
    container DynamicEntries {
      uses Boundary;
    }
  }
  /* device/boundary.proto */
  grouping BoundaryQoS {
    container QueueListRange {
      uses Boundary;
    }
    container CoSRange {
      uses Boundary;
    }
    container DSCPRange {
      uses Boundary;
    }
    container WRRRange {
      uses Boundary;
    }
  }
  /* device/boundary.proto */
  grouping BoundaryPoE {
    container BudgetRange {
      uses Boundary;
    }
  }
  /* device/boundary.proto */
  grouping BoundaryFiles {
    container CertificatedRange {
      uses Boundary;
    }
  }
  /* device/boundary.proto */
  grouping BoundaryTimeRange {
    container EntryRange {
      uses Boundary;
    }
  }
  /* device/boundary.proto */
  grouping BoundaryMonitor {
    container Temperature {
      uses Boundary;
    }
    container Power {
      uses Boundary;
    }
    container Cpu {
      uses Boundary;
    }
    container Memory {
      uses Boundary;
    }
    container PowerRedundantConsumption {
      uses Boundary;
    }
    container PowerRedundantTemperature {
      uses Boundary;
    }
    container PowerRedundantVoltage {
      uses Boundary;
    }
    container PowerRedundantCurrent {
      uses Boundary;
    }
  }
  /* device/fcl.proto */
  grouping FunctionControlAll {
    container VLAN {
      uses FunctionControlVLAN;
    }
    container Acl {
      uses FunctionControlACL;
    }
    container Mirroring {
      uses FunctionControlMirroring;
    }
    container FDB {
      uses FunctionControlFDB;
    }
  }
  /* device/fcl.proto */
  grouping FunctionControlVLAN {
    leaf Voice {
      type boolean;
    }
    leaf SelectiveQinq {
      type boolean;
    }
    leaf MACBased {
      type boolean;
    }
    leaf SubnetBased {
      type boolean;
    }
    leaf ProtocolBased {
      type boolean;
    }
    leaf Translation {
      type boolean;
    }
  }
  /* device/fcl.proto */
  grouping FunctionControlACL {
    leaf TimeRange {
      type boolean;
    }
    leaf Binding {
      type boolean;
    }
    leaf FlowMirroring {
      type boolean;
    }
  }
  /* device/fcl.proto */
  grouping FunctionControlMirroring {
    leaf RSPAN {
      type boolean;
    }
  }
  /* device/fcl.proto */
  grouping FunctionControlFDB {
    leaf PortSecurity {
      type boolean;
    }
    leaf LearningLimit {
      type boolean;
    }
    leaf Forward {
      type boolean;
    }
    leaf Drop {
      type boolean;
    }
  }
  /* device/path.proto */
  grouping PathAll {
    leaf LogRamDisk {
      type string;
    }
    leaf LogFlash {
      type string;
    }
    leaf ConfigDefault {
      type string;
    }
    leaf ConfigSaved {
      type string;
    }
    leaf User {
      type string;
    }
    leaf IPTables {
      type string;
    }
    leaf CoreReboot {
      type string;
    }
    leaf WarmStart {
      type string;
    }
    leaf VlanMgmt {
      type string;
    }
    leaf TimeCfg {
      type string;
    }
    leaf BootReady {
      type string;
    }
    leaf IPv6LinkLocal {
      type string;
    }
    leaf TimeZone {
      type string;
    }
    leaf Resolv {
      type string;
    }
    leaf DropbearProc {
      type string;
    }
    leaf TelnetProc {
      type string;
    }
    leaf FTPProc {
      type string;
    }
    leaf LocalUser {
      type string;
    }
    leaf Certificates {
      type string;
    }
    leaf OpenSSLCertificates {
      type string;
    }
    leaf SNMPdCertificates {
      type string;
    }
    leaf SNMPdCertificatesKey {
      type string;
    }
    leaf NetCfg {
      type string;
    }
    leaf IPv4Script {
      type string;
    }
    leaf IPv6Script {
      type string;
    }
    leaf LastSaveTime {
      type string;
    }
    leaf Image {
      type string;
    }
    leaf AltVersion {
      type string;
    }
    leaf AltBuildDateTime {
      type string;
    }
    leaf Version {
      type string;
    }
    leaf BuildDateTime {
      type string;
    }
    leaf DhcpServerDnsmasqLeasePath {
      type string;
    }
    leaf DhcpServerDnsmasqCfgPath {
      type string;
    }
    leaf DhcpServerPortBasedInfo {
      type string;
    }
  }
  /* device/device.proto */
  grouping InterfaceIdentify {
    leaf Type {
      type InterfaceTypeOptions;
    }
    leaf DeviceID {
      type int32;
    }
    leaf PortNo {
      type int32;
    }
    leaf LAGNo {
      type int32;
    }
    leaf VlanID {
      type int32;
    }
  }
  /* device/device.proto */
  grouping Info {
    leaf Model {
      type string;
    }
    leaf MACAddr {
      type string;
    }
    leaf MACAddrFactory {
      type string;
    }
    leaf SerialNo {
      type string;
    }
    leaf Vendor {
      type string;
    }
    leaf AltBuildDateTime {
      type string;
    }
    leaf CurrentBuildDateTime {
      type string;
    }
    leaf AltSwVersion {
      type string;
    }
    leaf CurrentSwVersion {
      type string;
    }
    leaf HwVersion {
      type string;
    }
    leaf CurrentImage {
      type string;
    }
    leaf Board {
      type string;
    }
    leaf Layer {
      type LayerTypeOptions;
    }
  }
  /* device/common.proto */
  grouping PortList {
    container List {
      list List_Entry {
        uses InterfaceIdentify;
      }
    }
  }


  /* **************************************************************************************************
   * Services    : 1                                                                                  *
   ************************************************************************************************** */

  /* **************************************************************************************************
   * Service     : Device                                                                             *
   * Methods     : 12                                                                                 *
   ************************************************************************************************** */
  /* device/service.proto */
  rpc intri-device-GetMACAddress {
    output  {
      uses intri-common:MACAddress;
    }
  }
  /* device/service.proto */
  rpc intri-device-GetPortLists {
    output  {
      uses PortList;
    }
  }
  /* device/service.proto */
  rpc intri-device-GetLAGPortLists {
    output  {
      uses PortList;
    }
  }
  /* device/service.proto */
  rpc intri-device-GetPoEPortLists {
    output  {
      uses PortList;
    }
  }
  /* device/service.proto */
  rpc intri-device-GetHardwareTableSize {
    output  {
      uses HardwareTableSize;
    }
  }
  /* device/service.proto */
  rpc intri-device-GetDeviceInfo {
    output  {
      uses Info;
    }
  }
  /* device/service.proto */
  rpc intri-device-GetBoardInfo {
    output  {
      uses BoardInfo;
    }
  }
  /* device/service.proto */
  rpc intri-device-GetHardwareInfo {
    output  {
      uses HardwareInfo;
    }
  }
  /* device/service.proto */
  rpc intri-device-GetFunctionControl {
    output  {
      uses FunctionControlAll;
    }
  }
  /* device/service.proto */
  rpc intri-device-GetBoundary {
    output  {
      uses BoundaryAll;
    }
  }
  /* device/service.proto */
  rpc intri-device-GetPath {
    output  {
      uses PathAll;
    }
  }
  /* device/service.proto */
  rpc intri-device-GetTimeControlInfo {
    output  {
      uses TimeControlInfo;
    }
  }

}
