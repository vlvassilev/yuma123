/*
 * This module has been generated by smidump 0.4.6:
 *
 *      smidump -f yang --yang-smi-extensions NETWORK-SERVICES-MIB
 *
 * Do not edit. Edit the source file instead!
 */

module NETWORK-SERVICES-MIB {

   /*** NAMESPACE / PREFIX DEFINITION ***/

   namespace "urn:ietf:params:xml:ns:yang:smiv2:NETWORK-SERVICES-MIB";
   prefix "network-services";

   /*** LINKAGE (IMPORTS / INCLUDES) ***/

   import SNMP-FRAMEWORK-MIB { prefix "snmp-framework"; }
   import yang-smi           { prefix "smi"; }
   import yang-types         { prefix "yang"; }

   /*** META INFORMATION ***/

   organization     
     "IETF Mail and Directory Management Working Group";

   contact          
     "        Ned Freed
      
      Postal: Innosoft International, Inc.
              1050 Lakes Drive
              West Covina, CA 91790
              US
      
         Tel: +1 626 919 3600
         Fax: +1 626 919 3614
      
      E-Mail: ned.freed@innosoft.com";

   description      
     "The MIB module describing network service applications";

   revision "2000-03-03" {
      description   
        "This revision, published in RFC 2788, changes a number of
         DisplayStrings to SnmpAdminStrings. Note that this change
         is not strictly supported by SMIv2.  However, the alternative
         of deprecating the old objects and defining new objects
         would have a more adverse impact on backward compatibility
         and interoperability, given the particular semantics of
         these objects. The defining reference for distinguished
         names has also been updated from RFC 1779 to RFC 2253.";
   }
   revision "1999-05-12" {
      description   
        "This revision fixes a few small technical problems found
         in previous versions, mostly in regards to the conformance
         groups for different versions of this MIB.  No changes have
         been made to the objects this MIB defines since RFC 2248.";
   }
   revision "1997-08-17" {
      description   
        "This revision, published in RFC 2248, adds the
         applDescription and applURL objects, adds the quiescing
         state to the applOperStatus object and renames the MIB
         from the APPLICATION-MIB to the NETWORK-SERVICE-MIB.";
   }
   revision "1993-11-28" {
      description   
        "The original version of this MIB was published in RFC 1565";
   }

   /*** TYPE DEFINITIONS ***/

   typedef DistinguishedName {
      type string {
         length "0..255";
         pattern "\p{IsBasicLatin}{0,255}";
      }
      description   
        "A Distinguished Name represented in accordance with
         RFC 2253, presented in the UTF-8 charset defined in
         RFC 2279.";
      smi:display-hint "255a";
   }

   typedef URLString {
      type string {
         length "0..255";
         pattern "\p{IsBasicLatin}{0,255}";
      }
      description   
        "A Uniform Resource Locator represented in accordance
         with RFCs 1738 and 2368, presented in the NVT ASCII
         charset defined in RFC 854.";
      smi:display-hint "255a";
   }

   container application {


      /* XXX table comments here XXX */

      list applEntry {

         key "applIndex";
         description 
           "An entry associated with a single network service
            application.";
         smi:oid "1.3.6.1.2.1.27.1.1";


         leaf applIndex {
            type int32 {
               range "1..2147483647";
            }
            config false;
            description   
              "An index to uniquely identify the network service
               application. This attribute is the index used for
               lexicographic ordering of the table.";
            smi:oid "1.3.6.1.2.1.27.1.1.1";
         }

         leaf applName {
            type snmp-framework:SnmpAdminString;
            config false;
            description   
              "The name the network service application chooses to be
               known by.";
            smi:oid "1.3.6.1.2.1.27.1.1.2";
         }

         leaf applDirectoryName {
            type network-services:DistinguishedName;
            config false;
            description   
              "The Distinguished Name of the directory entry where
               static information about this application is stored.
               An empty string indicates that no information about
               the application is available in the directory.";
            smi:oid "1.3.6.1.2.1.27.1.1.3";
         }

         leaf applVersion {
            type snmp-framework:SnmpAdminString;
            config false;
            description   
              "The version of network service application software.
               This field is usually defined by the vendor of the
               network service application software.";
            smi:oid "1.3.6.1.2.1.27.1.1.4";
         }

         leaf applUptime {
            type yang:timestamp;
            config false;
            description   
              "The value of sysUpTime at the time the network service
               application was last initialized.  If the application was
               last initialized prior to the last initialization of the
               network management subsystem, then this object contains
               a zero value.";
            smi:oid "1.3.6.1.2.1.27.1.1.5";
         }

         leaf applOperStatus {
            type enumeration {
               enum up         { value 1; }
               enum down       { value 2; }
               enum halted     { value 3; }
               enum congested  { value 4; }
               enum restarting { value 5; }
               enum quiescing  { value 6; }
            }
            config false;
            description   
              "Indicates the operational status of the network service
               application. 'down' indicates that the network service is
               
               not available. 'up' indicates that the network service
               is operational and available.  'halted' indicates that the
               service is operational but not available.  'congested'
               indicates that the service is operational but no additional
               inbound associations can be accommodated.  'restarting'
               indicates that the service is currently unavailable but is
               in the process of restarting and will be available soon.
               'quiescing' indicates that service is currently operational
               but is in the process of shutting down. Additional inbound
               associations may be rejected by applications in the
               'quiescing' state.";
            smi:oid "1.3.6.1.2.1.27.1.1.6";
         }

         leaf applLastChange {
            type yang:timestamp;
            config false;
            description   
              "The value of sysUpTime at the time the network service
               application entered its current operational state.  If
               the current state was entered prior to the last
               initialization of the local network management subsystem,
               then this object contains a zero value.";
            smi:oid "1.3.6.1.2.1.27.1.1.7";
         }

         leaf applInboundAssociations {
            type yang:gauge32;
            config false;
            description   
              "The number of current associations to the network service
               application, where it is the responder.  An inbound
               association occurs when another application successfully
               connects to this one.";
            smi:oid "1.3.6.1.2.1.27.1.1.8";
         }

         leaf applOutboundAssociations {
            type yang:gauge32;
            config false;
            description   
              "The number of current associations to the network service
               application, where it is the initiator.  An outbound
               association occurs when this application successfully
               connects to another one.";
            smi:oid "1.3.6.1.2.1.27.1.1.9";
         }

         leaf applAccumulatedInboundAssociations {
            type yang:counter32;
            config false;
            description   
              "The total number of associations to the application entity
               since application initialization, where it was the responder.";
            smi:oid "1.3.6.1.2.1.27.1.1.10";
         }

         leaf applAccumulatedOutboundAssociations {
            type yang:counter32;
            config false;
            description   
              "The total number of associations to the application entity
               since application initialization, where it was the initiator.";
            smi:oid "1.3.6.1.2.1.27.1.1.11";
         }

         leaf applLastInboundActivity {
            type yang:timestamp;
            config false;
            description   
              "The value of sysUpTime at the time this application last
               had an inbound association.  If the last association
               occurred prior to the last initialization of the network
               subsystem, then this object contains a zero value.";
            smi:oid "1.3.6.1.2.1.27.1.1.12";
         }

         leaf applLastOutboundActivity {
            type yang:timestamp;
            config false;
            description   
              "The value of sysUpTime at the time this application last
               had an outbound association.  If the last association
               occurred prior to the last initialization of the network
               subsystem, then this object contains a zero value.";
            smi:oid "1.3.6.1.2.1.27.1.1.13";
         }

         leaf applRejectedInboundAssociations {
            type yang:counter32;
            config false;
            description   
              "The total number of inbound associations the application
               entity has rejected, since application initialization.
               Rejected associations are not counted in the accumulated
               association totals.  Note that this only counts
               
               associations the application entity has rejected itself;
               it does not count rejections that occur at lower layers
               of the network.  Thus, this counter may not reflect the
               true number of failed inbound associations.";
            smi:oid "1.3.6.1.2.1.27.1.1.14";
         }

         leaf applFailedOutboundAssociations {
            type yang:counter32;
            config false;
            description   
              "The total number associations where the application entity
               is initiator and association establishment has failed,
               since application initialization.  Failed associations are
               not counted in the accumulated association totals.";
            smi:oid "1.3.6.1.2.1.27.1.1.15";
         }

         leaf applDescription {
            type snmp-framework:SnmpAdminString;
            config false;
            description   
              "A text description of the application.  This information
               is intended to identify and briefly describe the
               application in a status display.";
            smi:oid "1.3.6.1.2.1.27.1.1.16";
         }

         leaf applURL {
            type network-services:URLString;
            config false;
            description   
              "A URL pointing to a description of the application.
               This information is intended to identify and describe
               the application in a status display.";
            smi:oid "1.3.6.1.2.1.27.1.1.17";
         }
      }


      /* XXX table comments here XXX */

      list assocEntry {

         key "applIndex assocIndex";
         description 
           "An entry associated with an association for a network
            service application.";
         smi:oid "1.3.6.1.2.1.27.2.1";

         leaf applIndex {
            type leafref {
               path "/network-services:application/network-services:applEntry/network-services:applIndex";
            }
            config false;
            description   
              "Automagically generated leafref leaf.";
         }

         leaf assocIndex {
            type int32 {
               range "1..2147483647";
            }
            config false;
            description   
              "An index to uniquely identify each association for a network
               service application.  This attribute is the index that is
               used for lexicographic ordering of the table.  Note that the
               table is also indexed by the applIndex.";
            smi:oid "1.3.6.1.2.1.27.2.1.1";
         }

         leaf assocRemoteApplication {
            type snmp-framework:SnmpAdminString;
            config false;
            description   
              "The name of the system running remote network service
               application.  For an IP-based application this should be
               either a domain name or IP address.  For an OSI application
               it should be the string encoded distinguished name of the
               managed object.  For X.400(1984) MTAs which do not have a
               Distinguished Name, the RFC 2156 syntax 'mta in
               
               globalid' used in X400-Received: fields can be used. Note,
               however, that not all connections an MTA makes are
               necessarily to another MTA.";
            smi:oid "1.3.6.1.2.1.27.2.1.2";
         }

         leaf assocApplicationProtocol {
            type yang:object-identifier;
            config false;
            description   
              "An identification of the protocol being used for the
               application.  For an OSI Application, this will be the
               Application Context.  For Internet applications, OID
               values of the form {applTCPProtoID port} or {applUDPProtoID
               port} are used for TCP-based and UDP-based protocols,
               respectively. In either case 'port' corresponds to the
               primary port number being used by the protocol. The
               usual IANA procedures may be used to register ports for
               new protocols.";
            smi:oid "1.3.6.1.2.1.27.2.1.3";
         }

         leaf assocApplicationType {
            type enumeration {
               enum uainitiator   { value 1; }
               enum uaresponder   { value 2; }
               enum peerinitiator { value 3; }
               enum peerresponder { value 4; }
            }
            config false;
            description   
              "This indicates whether the remote application is some type of
               client making use of this network service (e.g., a Mail User
               Agent) or a server acting as a peer. Also indicated is whether
               the remote end initiated an incoming connection to the network
               service or responded to an outgoing connection made by the
               local application.  MTAs and messaging gateways are
               considered to be peers for the purposes of this variable.";
            smi:oid "1.3.6.1.2.1.27.2.1.4";
         }

         leaf assocDuration {
            type yang:timestamp;
            config false;
            description   
              "The value of sysUpTime at the time this association was
               started.  If this association started prior to the last
               initialization of the network subsystem, then this
               object contains a zero value.";
            smi:oid "1.3.6.1.2.1.27.2.1.5";
         }
      }



      smi:oid "1.3.6.1.2.1.27";
   }

} /* end of module NETWORK-SERVICES-MIB */
