module intri-common {

  namespace "intri:intri-common";
  prefix "intri-common";
  organization "
    Intrising Inc.";
  contact "
    intrising@intrising.com.tw";
  revision 2022-06-24 {
    description "Build date.";
  }

  typedef IPv6ScopeTypeOptions {
    type enumeration {
      enum IPV6_SCOPE_TYPE_LINK {
        description "[Link]";
        value 0;
      }
      enum IPV6_SCOPE_TYPE_SITE {
        description "[Site]";
        value 1;
      }
      enum IPV6_SCOPE_TYPE_GLOBAL {
        description "[Global]";
        value 2;
      }
      enum IPV6_SCOPE_TYPE_OTHER {
        description "[Other]";
        value 3;
      }
    }
  }
  grouping Path {
    leaf Path {
      mandatory "true";
      type string;
    }
  }
  grouping ExportPathRequest {
    leaf Path {
      mandatory "true";
      type string;
    }
    leaf FTPSEnabled {
      mandatory "true";
      type boolean;
    }
  }
  grouping ImportPathRequest {
    leaf Path {
      mandatory "true";
      type string;
    }
    leaf FTPSEnabled {
      mandatory "true";
      type boolean;
    }
    leaf RebootAfterAction {
      mandatory "true";
      type boolean;
    }
  }
  grouping Enabled {
    leaf IsEnabled {
      mandatory "true";
      type boolean;
    }
  }
  grouping MACAddress {
    leaf MACAddr {
      mandatory "true";
      type string;
    }
  }
  grouping IPAddress {
    leaf IPAddr {
      mandatory "true";
      type string;
    }
  }
  grouping IPv4List {
    container List {
      leaf-list List_Entry {
        type string;
      }
    }
  }
  grouping IPv6Entry {
    leaf Type {
      mandatory "true";
      type IPv6ScopeTypeOptions;
    }
    leaf IPAddr {
      mandatory "true";
      type string;
    }
  }
  grouping IPv6List {
    container List {
      list List_Entry {
        uses IPv6Entry;
      }
    }
  }
  grouping Name {
    leaf Name {
      mandatory "true";
      type string;
    }
  }
  grouping NameList {
    container NameList {
      leaf-list NameList_Entry {
        type string;
      }
    }
  }
  grouping Reply {
    leaf Reply {
      mandatory "true";
      type string;
    }
  }
  grouping Confirm {
    leaf Confirm {
      mandatory "true";
      type string;
    }
  }
  grouping DateTime {
    leaf Ts {
      mandatory "true";
      type string;
    }
  }
  grouping AllStatus {
    leaf Status {
      mandatory "true";
      type string;
    }
  }
  grouping State {
    leaf State {
      mandatory "true";
      type boolean;
    }
  }
  grouping Index {
    leaf Index {
      mandatory "true";
      type int32;
    }
  }
}
