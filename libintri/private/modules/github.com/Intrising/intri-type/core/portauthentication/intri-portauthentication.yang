// Code generated by protoc-gen-yang. DO NOT EDIT.


/* ****************************************************************************************************
 * Import Path : "github.com/Intrising/intri-type/core/portauthentication"                            *
 * Dir Path    : github.com/Intrising/intri-type/core/portauthentication                              *
 * Go Package  : portauthentication                                                                   *
 * Files       : 3                                                                                    *
 **************************************************************************************************** */
module intri-portauthentication {

  namespace "intri:intri-portauthentication";

  prefix "intri-portauthentication";

  organization "Intrising Inc.";

  contact "intrising@intrising.com.tw";

  revision 2022-06-23 {
    description "Build date.";
  }

  import intri-device {
    prefix intri-device;
  }
  import intri-empty {
    prefix intri-empty;
  }
  import intri-common {
    prefix intri-common;
  }
  import intri-access {
    prefix intri-access;
  }


  /* **************************************************************************************************
   * Enums       : 7                                                                                  *
   ************************************************************************************************** */
  /* core/portauthentication/common.proto */
  typedef AuthorizationStateTypeOptions {
    type enumeration {
      enum AUTHORIZATION_STATE_TYPE_UNDEFINED {
        description "[Undefined]";
        value 0;
      }
      enum AUTHORIZATION_STATE_TYPE_DISABLED {
        description "[Disabled]";
        value 1;
      }
      enum AUTHORIZATION_STATE_TYPE_UNAUTHORIZED {
        description "[Unauthorized]";
        value 2;
      }
      enum AUTHORIZATION_STATE_TYPE_PROCESSING {
        description "[Processing]";
        value 3;
      }
      enum AUTHORIZATION_STATE_TYPE_AUTHORIZED {
        description "[Authorized]";
        value 4;
      }
      enum AUTHORIZATION_STATE_TYPE_REJECTED {
        description "[Rejected]";
        value 5;
      }
    }
  }
  /* core/portauthentication/common.proto */
  typedef AuthorizationModeTypeOptions {
    type enumeration {
      enum AUTHORIZATION_MODE_TYPE_ALWAYSAUTH {
        description "[Always Auth]";
        value 0;
      }
      enum AUTHORIZATION_MODE_TYPE_FORCEUNAUTH {
        description "[Force Unauth]";
        value 1;
      }
      enum AUTHORIZATION_MODE_TYPE_VIAMACTABLE {
        description "[Via MAC Table]";
        value 2;
      }
      enum AUTHORIZATION_MODE_TYPE_MACVIARADIUS {
        description "[MAC via RADIUS]";
        value 3;
      }
      enum AUTHORIZATION_MODE_TYPE_8021XVIARADIUS {
        description "[802.1X via RADIUS]";
        value 4;
      }
      enum AUTHORIZATION_MODE_TYPE_MAC8021XVIARADIUS {
        description "[MAC 802.1X via RADIUS]";
        value 5;
      }
      enum AUTHORIZATION_MODE_TYPE_8021XMACVIARADIUS {
        description "[802.1X MAC via RADIUS]";
        value 6;
      }
      enum AUTHORIZATION_MODE_TYPE_NONE {
        description "*internal";
        value 9;
      }
    }
  }
  /* core/portauthentication/common.proto */
  typedef UnAuthorizationModeTypeOptions {
    type enumeration {
      enum UNAUTHORIZATION_MODE_TYPE_BLOCKED {
        description "[Blocked]";
        value 0;
      }
      enum UNAUTHORIZATION_MODE_TYPE_USE_UNAUTHORIZEDVLAN {
        description "[Use Unauthorized VLAN]";
        value 1;
      }
      enum UNAUTHORIZATION_MODE_TYPE_INCOMING_BLOCKED {
        description "[Incoming Blocked]";
        value 2;
      }
    }
  }
  /* core/portauthentication/common.proto */
  typedef MACSpellingTypeOptions {
    type enumeration {
      enum MAC_SPELLING_TYPE_LOWERCASE {
        description "[Lowercase]";
        value 0;
      }
      enum MAC_SPELLING_TYPE_UPPERCASE {
        description "[Uppercase]";
        value 1;
      }
    }
  }
  /* core/portauthentication/common.proto */
  typedef MACPasswordSourceTypeOptions {
    type enumeration {
      enum MAC_PASSWORD_SOURCE_TYPE_USEMAC {
        description "[Use MAC]";
        value 0;
      }
      enum MAC_PASSWORD_SOURCE_TYPE_USEPASSWORD {
        description "[Use Password]";
        value 1;
      }
    }
  }
  /* core/portauthentication/common.proto */
  typedef EntryStateTypeOptions {
    type enumeration {
      enum ENTRY_STATE_TYPE_UNUSED {
        description "[Unused]";
        value 0;
      }
      enum ENTRY_STATE_TYPE_INACTIVE {
        description "[Inactive]";
        value 1;
      }
      enum ENTRY_STATE_TYPE_ACTIVE {
        description "[Active]";
        value 2;
      }
    }
  }
  /* core/portauthentication/common.proto */
  typedef MACTimeoutTypeOptions {
    type enumeration {
      enum MAC_TIMEOUT_TYPE_NONE {
        description "[None]";
        value 0;
      }
      enum MAC_TIMEOUT_TYPE_SLOW {
        description "[Slow]";
        value 1;
      }
    }
  }


  /* **************************************************************************************************
   * Msgs        : 14                                                                                 *
   ************************************************************************************************** */
  /* core/portauthentication/portauthentication.proto */
  grouping Config {
    container SystemConfig {
      uses SystemConfig;
    }
    container PortConfig {
      uses PortConfig;
    }
    container AuthorizedMACs {
      uses AuthorizedMACs;
    }
  }
  /* core/portauthentication/portauthentication.proto */
  grouping AuthorizedMACsEntry {
    leaf Name {
      type string;
    }
    leaf MACAddress {
      type string;
    }
    container PermittedPortList {
      list PermittedPortList_Entry {
        uses intri-device:InterfaceIdentify;
      }
    }
    leaf TreatAsVendorMAC {
      type boolean;
    }
  }
  /* core/portauthentication/portauthentication.proto */
  grouping AuthorizedMACs {
    container List {
      list List_Entry {
        uses AuthorizedMACsEntry;
      }
    }
  }
  /* core/portauthentication/portauthentication.proto */
  grouping SystemConfig {
    leaf PortAccessControlEnabled {
      type boolean;
    }
    leaf ReauthenticationPeriod {
      type int32;
    }
    leaf NASIdentifier {
      type string;
    }
    leaf MACSeparatorChar {
      type string;
    }
    leaf MACSpelling {
      type MACSpellingTypeOptions;
    }
    leaf MACPasswordSource {
      type MACPasswordSourceTypeOptions;
    }
    leaf MACPasswordString {
      type string;
    }
    leaf PrimaryAuthServerName {
      type string;
    }
    leaf PrimaryAcctServerName {
      type string;
    }
    leaf FallbackAuthServerName {
      type string;
    }
    leaf FallbackAcctServerName {
      type string;
    }
    leaf ServerDownTimeout {
      type int32;
    }
  }
  /* core/portauthentication/portauthentication.proto */
  grouping PortConfig {
    container List {
      list List_Entry {
        uses PortConfigEntry;
      }
    }
  }
  /* core/portauthentication/portauthentication.proto */
  grouping PortConfigEntry {
    container IdentifyNo {
      uses intri-device:InterfaceIdentify;
    }
    leaf AuthorizedMode {
      type AuthorizationModeTypeOptions;
    }
    leaf UnAuthorizedMode {
      type UnAuthorizationModeTypeOptions;
    }
    leaf AuthFailRetryInterval {
      type int32;
    }
    leaf LimitedNumberOfMACs {
      type int32;
    }
    leaf MACTimeout {
      type MACTimeoutTypeOptions;
    }
  }
  /* core/portauthentication/portauthentication.proto */
  grouping PortStatus {
    container List {
      list List_Entry {
        uses PortStatusEntry;
      }
    }
  }
  /* core/portauthentication/portauthentication.proto */
  grouping PortStatusEntry {
    container IdentifyNo {
      uses intri-device:InterfaceIdentify;
    }
    leaf AuthorizationState {
      type AuthorizationStateTypeOptions;
    }
    leaf AuthorizationMode {
      type AuthorizationModeTypeOptions;
    }
    leaf LastStateChange {
      type string;
    }
    leaf NumberOfMACsToLearn {
      type int32;
    }
    leaf NumberOfLearnedMACs {
      type int32;
    }
  }
  /* core/portauthentication/portauthentication.proto */
  grouping PortAuthorizationStatus {
    container List {
      list List_Entry {
        uses PortAuthorizationStatusEntry;
      }
    }
  }
  /* core/portauthentication/portauthentication.proto */
  grouping PortAuthorizationStatusEntry {
    container IdentifyNo {
      uses intri-device:InterfaceIdentify;
    }
    leaf AuthorizationState {
      type AuthorizationStateTypeOptions;
    }
    leaf UserMAC {
      type string;
    }
    leaf UserName {
      type string;
    }
    leaf IdleTimeout {
      type int32;
    }
    leaf SessionTimeout {
      type int32;
    }
    leaf LastStateChange {
      type string;
    }
  }
  /* core/portauthentication/portauthentication.proto */
  grouping UserStatus {
    container List {
      list List_Entry {
        uses UserStatusEntry;
      }
    }
  }
  /* core/portauthentication/portauthentication.proto */
  grouping UserStatusEntry {
    leaf EntryState {
      type EntryStateTypeOptions;
    }
    leaf AuthorizationState {
      type AuthorizationStateTypeOptions;
    }
    leaf AuthorizationMode {
      type AuthorizationModeTypeOptions;
    }
    container IdentifyNo {
      uses intri-device:InterfaceIdentify;
    }
    leaf UserMAC {
      type string;
    }
    leaf UserName {
      type string;
    }
    leaf VlanID {
      type int32;
    }
    leaf IdleTimeout {
      type int32;
    }
    leaf SessionTimeout {
      type int32;
    }
    leaf LoginTimeStamp {
      type string;
    }
  }
  /* core/portauthentication/portauthentication.proto */
  grouping LearnMACNowEntry {
    container IdentifyNo {
      uses intri-device:InterfaceIdentify;
    }
    leaf Amount {
      type int32;
    }
  }
  /* core/portauthentication/portauthentication.proto */
  grouping UnauthorizeMACEntry {
    container IdentifyNo {
      uses intri-device:InterfaceIdentify;
    }
    leaf MACAddress {
      type string;
    }
  }


  /* **************************************************************************************************
   * Services    : 1                                                                                  *
   ************************************************************************************************** */

  /* **************************************************************************************************
   * Service     : PortAuthentication                                                                 *
   * Methods     : 17                                                                                 *
   ************************************************************************************************** */
  /* core/portauthentication/service.proto */
  rpc intri-portauthentication-GetConfig {
    output  {
      uses Config;
    }
  }
  /* core/portauthentication/service.proto */
  rpc intri-portauthentication-GetSystemConfig {
    output  {
      uses SystemConfig;
    }
  }
  /* core/portauthentication/service.proto */
  rpc intri-portauthentication-SetSystemConfig {
    input  {
      uses SystemConfig;
    }
  }
  /* core/portauthentication/service.proto */
  rpc intri-portauthentication-GetPortConfig {
    output  {
      uses PortConfig;
    }
  }
  /* core/portauthentication/service.proto */
  rpc intri-portauthentication-UpdatePortConfig {
    input  {
      uses PortConfig;
    }
  }
  /* core/portauthentication/service.proto */
  rpc intri-portauthentication-GetAuthorizedMACsConfig {
    output  {
      uses AuthorizedMACs;
    }
  }
  /* core/portauthentication/service.proto */
  rpc intri-portauthentication-AddAuthorizedMACsEntryConfig {
    input  {
      uses AuthorizedMACsEntry;
    }
  }
  /* core/portauthentication/service.proto */
  rpc intri-portauthentication-DeleteAuthorizedMACsEntryConfig {
    input  {
      uses intri-common:Name;
    }
  }
  /* core/portauthentication/service.proto */
  rpc intri-portauthentication-UpdateAuthorizedMACsEntryConfig {
    input  {
      uses AuthorizedMACsEntry;
    }
  }
  /* core/portauthentication/service.proto */
  rpc intri-portauthentication-GetPortStatus {
    output  {
      uses PortStatus;
    }
  }
  /* core/portauthentication/service.proto */
  rpc intri-portauthentication-GetMACAuthorizationStatus {
    output  {
      uses PortAuthorizationStatus;
    }
  }
  /* core/portauthentication/service.proto */
  rpc intri-portauthentication-Get8021XAuthorizationStatus {
    output  {
      uses PortAuthorizationStatus;
    }
  }
  /* core/portauthentication/service.proto */
  rpc intri-portauthentication-GetUserStatus {
    output  {
      uses UserStatus;
    }
  }
  /* core/portauthentication/service.proto */
  rpc intri-portauthentication-RunPortConfigLearnMACNow {
    input  {
      uses LearnMACNowEntry;
    }
  }
  /* core/portauthentication/service.proto */
  rpc intri-portauthentication-RunPortConfigReauthenticate {
    input  {
      uses intri-device:InterfaceIdentify;
    }
  }
  /* core/portauthentication/service.proto */
  rpc intri-portauthentication-RunPortConfigUnauthorizeMAC {
    input  {
      uses UnauthorizeMACEntry;
    }
  }
  /* core/portauthentication/service.proto */
  rpc intri-portauthentication-SetAuthenticationServers {
    input  {
      uses intri-access:AuthenticationServersConfig;
    }
  }

}
