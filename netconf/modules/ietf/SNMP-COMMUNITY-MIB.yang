/*
 * This module has been generated by smidump 0.4.6:
 *
 *      smidump -f yang --yang-smi-extensions SNMP-COMMUNITY-MIB
 *
 * Do not edit. Edit the source file instead!
 */

module SNMP-COMMUNITY-MIB {

   /*** NAMESPACE / PREFIX DEFINITION ***/

   namespace "urn:ietf:params:xml:ns:yang:smiv2:SNMP-COMMUNITY-MIB";
   prefix "snmp-community";

   /*** LINKAGE (IMPORTS / INCLUDES) ***/

   import SNMP-FRAMEWORK-MIB { prefix "snmp-framework"; }
   import SNMP-TARGET-MIB    { prefix "snmp-target"; }
   import SNMPv2-TC          { prefix "smiv2"; }
   import inet-types         { prefix "inet"; }
   import yang-smi           { prefix "smi"; }

   /*** META INFORMATION ***/

   organization     
     "SNMPv3 Working Group";

   contact          
     "WG-email:   snmpv3@lists.tislabs.com
      Subscribe:  majordomo@lists.tislabs.com
                  In msg body:  subscribe snmpv3
      
      Chair:      Russ Mundy
                  TIS Labs at Network Associates
      Postal:     3060 Washington Rd
                  Glenwood MD 21738
                  USA
      Email:      mundy@tislabs.com
      Phone:      +1-301-854-6889
      
      Co-editor:  Rob Frye
                  CoSine Communications
      Postal:     1200 Bridge Parkway
                  Redwood City, CA 94065
                  USA
      E-mail:     rfrye@cosinecom.com
      Phone:      +1 703 725 1130
      
      Co-editor:  David B. Levi
                  Nortel Networks
      Postal:     3505 Kesterwood Drive
                  Knoxville, TN 37918
      E-mail:     dlevi@nortelnetworks.com
      Phone:      +1 423 686 0432
      
      Co-editor:  Shawn A. Routhier
                  Integrated Systems Inc.
      Postal:     333 North Ave 4th Floor
                  Wakefield, MA 01880
      E-mail:     sar@epilogue.com
      Phone:      +1 781 245 0804
      
      Co-editor:  Bert Wijnen
                  Lucent Technologies
      Postal:     Schagen 33
                  3461 GL Linschoten
                  Netherlands
      Email:      bwijnen@lucent.com
      Phone:      +31-348-407-775";

   description      
     "This MIB module defines objects to help support coexistence
      between SNMPv1, SNMPv2c, and SNMPv3.";

   revision "2000-03-06" {
      description   
        "This version published as RFC 2576.";
   }
   revision "1999-05-13" {
      description   
        "The Initial Revision";
   }

   container snmpCommunityMIBObjects {


      /* XXX table comments here XXX */

      list snmpCommunityEntry {

         key "snmpCommunityIndex";
         description 
           "Information about a particular community string.";
         smi:oid "1.3.6.1.6.3.18.1.1.1";


         leaf snmpCommunityIndex {
            type snmp-framework:SnmpAdminString {
               length "1..32";
            }
            config false;
            description   
              "The unique index value of a row in this table.";
            smi:oid "1.3.6.1.6.3.18.1.1.1.1";
         }

         leaf snmpCommunityName {
            type binary;
            config true;
            description   
              "The community string for which a row in this table
               represents a configuration.";
            smi:oid "1.3.6.1.6.3.18.1.1.1.2";
         }

         leaf snmpCommunitySecurityName {
            type snmp-framework:SnmpAdminString {
               length "1..32";
            }
            config true;
            description   
              "A human readable string representing the corresponding
               value of snmpCommunityName in a Security Model
               independent format.";
            smi:oid "1.3.6.1.6.3.18.1.1.1.3";
         }

         leaf snmpCommunityContextEngineID {
            type snmp-framework:SnmpEngineID;
            config true;
            description   
              "The contextEngineID indicating the location of the
               context in which management information is accessed
               when using the community string specified by the
               corresponding instance of snmpCommunityName.
               
               The default value is the snmpEngineID of the entity in
               which this object is instantiated.";
            smi:oid "1.3.6.1.6.3.18.1.1.1.4";
         }

         leaf snmpCommunityContextName {
            type snmp-framework:SnmpAdminString {
               length "0..32";
            }
            config true;
            description   
              "The context in which management information is accessed
               when using the community string specified by the corresponding
               instance of snmpCommunityName.";
            smi:default "";
            smi:oid "1.3.6.1.6.3.18.1.1.1.5";
         }

         leaf snmpCommunityTransportTag {
            type snmp-target:SnmpTagValue;
            config true;
            description   
              "This object specifies a set of transport endpoints
               from which a command responder application will accept
               management requests.  If a management request containing
               this community is received on a transport endpoint other
               than the transport endpoints identified by this object,
               the request is deemed unauthentic.
               
               The transports identified by this object are specified
               
               in the snmpTargetAddrTable.  Entries in that table
               whose snmpTargetAddrTagList contains this tag value
               are identified.
               
               If the value of this object has zero-length, transport
               endpoints are not checked when authenticating messages
               containing this community string.";
            smi:default "";
            smi:oid "1.3.6.1.6.3.18.1.1.1.6";
         }

         leaf snmpCommunityStorageType {
            type smiv2:StorageType;
            config true;
            description   
              "The storage type for this conceptual row in the
               snmpCommunityTable.  Conceptual rows having the value
               'permanent' need not allow write-access to any
               columnar object in the row.";
            smi:oid "1.3.6.1.6.3.18.1.1.1.7";
         }

         leaf snmpCommunityStatus {
            type smiv2:RowStatus;
            config true;
            description   
              "The status of this conceptual row in the snmpCommunityTable.
               
               An entry in this table is not qualified for activation
               until instances of all corresponding columns have been
               initialized, either through default values, or through
               Set operations.  The snmpCommunityName and
               snmpCommunitySecurityName objects must be explicitly set.
               
               There is no restriction on setting columns in this table
               when the value of snmpCommunityStatus is active(1).";
            smi:oid "1.3.6.1.6.3.18.1.1.1.8";
         }
      }


      leaf snmpTrapAddress {
         type inet:ipv4-address;
         config false;
         description 
           "The value of the agent-addr field of a Trap PDU which
            is forwarded by a proxy forwarder application using
            an SNMP version other than SNMPv1.  The value of this
            object SHOULD contain the value of the agent-addr field
            from the original Trap PDU as generated by an SNMPv1
            agent.";
         smi:oid "1.3.6.1.6.3.18.1.3";
      }

      leaf snmpTrapCommunity {
         type binary;
         config false;
         description 
           "The value of the community string field of an SNMPv1
            message containing a Trap PDU which is forwarded by a
            a proxy forwarder application using an SNMP version
            other than SNMPv1.  The value of this object SHOULD
            contain the value of the community string field from
            the original SNMPv1 message containing a Trap PDU as
            generated by an SNMPv1 agent.";
         smi:oid "1.3.6.1.6.3.18.1.4";
      }
      smi:oid "1.3.6.1.6.3.18.1";
   }


   /* XXX table comments here XXX */

   augment "/snmp-target:snmpTargetObjects/snmp-target:snmpTargetAddrEntry" {
      description   
        "Information about a particular mask and mms value.";

      leaf snmpTargetAddrTMask {
         type binary {
            length "0..255";
         }
         config true;
         description 
           "The mask value associated with an entry in the
            snmpTargetAddrTable.  The value of this object must
            have the same length as the corresponding instance of
            snmpTargetAddrTAddress, or must have length 0.  An
            attempt to set it to any other value will result in
            an inconsistentValue error.
            
            The value of this object allows an entry in the
            snmpTargetAddrTable to specify multiple addresses.
            The mask value is used to select which bits of
            a transport address must match bits of the corresponding
            instance of snmpTargetAddrTAddress, in order for the
            transport address to match a particular entry in the
            snmpTargetAddrTable.  Bits which are 1 in the mask
            value indicate bits in the transport address which
            must match bits in the snmpTargetAddrTAddress value.
            
            Bits which are 0 in the mask indicate bits in the
            transport address which need not match.  If the
            length of the mask is 0, the mask should be treated
            as if all its bits were 1 and its length were equal
            to the length of the corresponding value of
            snmpTargetAddrTable.
            
            This object may not be modified while the value of the
            corresponding instance of snmpTargetAddrRowStatus is
            active(1).  An attempt to set this object in this case
            will result in an inconsistentValue error.";
         smi:default "";
         smi:oid "1.3.6.1.6.3.18.1.2.1.1";
      }

      leaf snmpTargetAddrMMS {
         type int32 {
            range "0 | 484..2147483647";
         }
         config true;
         description 
           "The maximum message size value associated with an entry
            in the snmpTargetAddrTable.";
         smi:default "484";
         smi:oid "1.3.6.1.6.3.18.1.2.1.2";
      }
      smi:oid "1.3.6.1.6.3.18.1.2.1";
   }

} /* end of module SNMP-COMMUNITY-MIB */
