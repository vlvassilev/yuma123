module traffic-generator-testframe {
  yang-version 1.1;
  namespace "http://yuma123.org/ns/traffic-generator-testframe";
  prefix dt;

  import ietf-interfaces {
    prefix if;
  }
  import ietf-traffic-generator {
    prefix tg;
  }

  organization
    "yuma123.org";
  description
    "This module augments the traffic-generator configuration so that
     testframes with dynamic sequence number (8 octets) and timestamp in
     the last 10 octets (IEEE 1588 format - 6 octets seconds,
     4 octets nanoseconds) of the payload are generated.";

  revision 2020-08-11 {
    description
      "Added testframe-type identityref leaf to replace the boolean testframe.";
  }

  identity testframe {
    description
      "Base identity for all testframe types.";
  }

  identity testframe-ipv4-udp {
    base testframe;
    description
      "Base identity for ipv4-udp testframe.";
  }

  identity testframe-ethernet {
    base testframe;
    description
      "Base identity for ethernet testframe.";
  }

  augment "/if:interfaces/if:interface/tg:traffic-generator" {
    container testframe {
      leaf type {
        type identityref {
          base testframe;
        }
        description
          "When this leaf is present last 18 bytes of the payload
           contains dynamic sequence number (8 octets) followed
           by timestamp (10 octets).";
      }
    }
  }
}
