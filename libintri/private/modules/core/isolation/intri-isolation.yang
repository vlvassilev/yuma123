module intri-isolation {
  namespace "intri:intri-isolation";
  prefix "intri-isolation";
  import isolationpb {
    prefix "isolationpb";
  }
  organization "Intrising Inc.";
  contact "xxx@intrising.com.tw";
  revision 2022-06-14 {
    description "Build date.";
  }
}
