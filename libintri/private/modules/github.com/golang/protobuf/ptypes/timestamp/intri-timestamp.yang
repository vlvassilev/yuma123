// Code generated by protoc-gen-yang. DO NOT EDIT.


/* ****************************************************************************************************
 * Import Path : "github.com/golang/protobuf/ptypes/timestamp"                                        *
 * Dir Path    : github.com/golang/protobuf/ptypes/timestamp                                          *
 * Go Package  : timestamp                                                                            *
 * Files       : 1                                                                                    *
 **************************************************************************************************** */
module intri-timestamp {

  namespace "intri:intri-timestamp";

  prefix "intri-timestamp";

  organization "Intrising Inc.";

  contact "intrising@intrising.com.tw";

  revision 2022-06-23 {
    description "Build date.";
  }


  /* **************************************************************************************************
   * Msgs        : 1                                                                                  *
   ************************************************************************************************** */
  /* google/protobuf/timestamp.proto */
  grouping Timestamp {
    leaf Seconds {
      type int64;
    }
    leaf Nanos {
      type int32;
    }
  }

}
