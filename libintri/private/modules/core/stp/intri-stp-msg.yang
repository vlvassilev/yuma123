submodule intri-stp-msg {
  belongs-to "intri-stp" {
    prefix "intri-stp-msg";
  }
  include intri-stp-enum;
  import stppb {
    prefix "stppb";
  }
  revision 2022-06-14 {
    description "Build date.";
  }
  // core/stp/stp.proto
  grouping MSTPConfig {
    leaf MSTPConfig_Mode {
      type stppb:BridgeConfigModeTypeOptions;
    }
    leaf MSTPConfig_Name {
      type string;
    }
    leaf MSTPConfig_Revision {
      type int32;
    }
    leaf MSTPConfig_MaxAge {
      type int32;
    }
    leaf MSTPConfig_HelloTime {
      type int32;
    }
    leaf MSTPConfig_ForwardDelay {
      type int32;
    }
    leaf MSTPConfig_MaxHops {
      type int32;
    }
    leaf MSTPConfig_TxHoldCount {
      type int32;
    }
    container MSTPConfig_Cist {
      uses stppb:CISTEntry;
    }
    container MSTPConfig_Mstis {
      uses stppb:MSTIEntry;
    }
  }
  // core/stp/stp.proto
  grouping CISTEntry {
    leaf CISTEntry_No {
      type int32;
    }
    leaf CISTEntry_Priority {
      type int32;
    }
    container CISTEntry_Ports {
      uses stppb:MSTPCistPort;
    }
  }
  // core/stp/stp.proto
  grouping MSTIEntry {
    leaf MSTIEntry_No {
      type int32;
    }
    leaf MSTIEntry_Vlans {
      type int32;
    }
    leaf MSTIEntry_Enabled {
      type boolean;
    }
    leaf MSTIEntry_Priority {
      type int32;
    }
    container MSTIEntry_Ports {
      uses stppb:MSTPMstiPort;
    }
  }
  // core/stp/stp.proto
  grouping MSTIList {
    container MSTIList_List {
      uses stppb:MSTIEntry;
    }
  }
  // core/stp/stp.proto
  grouping MSTPCistPort {
    leaf MSTPCistPort_No {
      type int32;
    }
    leaf MSTPCistPort_PathCost {
      type int32;
    }
    leaf MSTPCistPort_Priority {
      type int32;
    }
    leaf MSTPCistPort_STPEnabled {
      type boolean;
    }
    leaf MSTPCistPort_P2PMode {
      type stppb:PortConfigAdminP2PPortTypeOptions;
    }
    leaf MSTPCistPort_EdgeMode {
      type boolean;
    }
    leaf MSTPCistPort_BPDUGuard {
      type stppb:PortConfigBPDUGuardTypeOptions;
    }
    leaf MSTPCistPort_RestrictRoot {
      type boolean;
    }
  }
  // core/stp/stp.proto
  grouping MSTPMstiPort {
    leaf MSTPMstiPort_No {
      type int32;
    }
    leaf MSTPMstiPort_PathCost {
      type int32;
    }
    leaf MSTPMstiPort_Priority {
      type int32;
    }
  }
  // core/stp/stp.proto
  grouping MSTPID {
    leaf MSTPID_MACAddress {
      type string;
    }
    leaf MSTPID_Priority {
      type int32;
    }
  }
  // core/stp/stp.proto
  grouping CISTStatus {
    leaf CISTStatus_No {
      type int32;
    }
    container CISTStatus_BridgeID {
      uses stppb:MSTPID;
    }
    container CISTStatus_RootID {
      uses stppb:MSTPID;
    }
    leaf CISTStatus_RootPort {
      type int32;
    }
    leaf CISTStatus_RootCost {
      type int32;
    }
    container CISTStatus_RegionalRoot {
      uses stppb:MSTPID;
    }
    leaf CISTStatus_InternalRootCost {
      type int32;
    }
    leaf CISTStatus_TopologyChange {
      type boolean;
    }
    leaf CISTStatus_TopologyChangeCount {
      type int32;
    }
    leaf CISTStatus_TimeSinceTopologyChange {
      type int32;
    }
    container CISTStatus_Ports {
      uses stppb:CISTPortEntryStatus;
    }
  }
  // core/stp/stp.proto
  grouping CISTPortEntryStatus {
    leaf CISTPortEntryStatus_No {
      type int32;
    }
    leaf CISTPortEntryStatus_Role {
      type string;
    }
    leaf CISTPortEntryStatus_State {
      type string;
    }
    leaf CISTPortEntryStatus_Priority {
      type int32;
    }
    leaf CISTPortEntryStatus_PathCost {
      type int32;
    }
    leaf CISTPortEntryStatus_EdgeMode {
      type boolean;
    }
    leaf CISTPortEntryStatus_P2PMode {
      type boolean;
    }
    leaf CISTPortEntryStatus_Uptime {
      type int32;
    }
    leaf CISTPortEntryStatus_BPDUGuard {
      type string;
    }
  }
  // core/stp/stp.proto
  grouping MSTIStatus {
    container MSTIStatus_List {
      uses stppb:MSTIStatusEntry;
    }
  }
  // core/stp/stp.proto
  grouping MSTIStatusEntry {
    leaf MSTIStatusEntry_No {
      type int32;
    }
    container MSTIStatusEntry_BridgeID {
      uses stppb:MSTPID;
    }
    container MSTIStatusEntry_RootID {
      uses stppb:MSTPID;
    }
    leaf MSTIStatusEntry_RootPort {
      type int32;
    }
    leaf MSTIStatusEntry_RootCost {
      type int32;
    }
    leaf MSTIStatusEntry_TopologyChange {
      type boolean;
    }
    leaf MSTIStatusEntry_TopologyChangeCount {
      type int32;
    }
    leaf MSTIStatusEntry_TimeSinceTopologyChange {
      type int32;
    }
    container MSTIStatusEntry_Ports {
      uses stppb:MSTIPortStatusEntry;
    }
  }
  // core/stp/stp.proto
  grouping MSTIPortStatusEntry {
    leaf MSTIPortStatusEntry_No {
      type int32;
    }
    leaf MSTIPortStatusEntry_Role {
      type string;
    }
    leaf MSTIPortStatusEntry_State {
      type string;
    }
    leaf MSTIPortStatusEntry_Priority {
      type int32;
    }
    leaf MSTIPortStatusEntry_PathCost {
      type int32;
    }
    leaf MSTIPortStatusEntry_Uptime {
      type int32;
    }
  }
  // core/stp/stp.proto
  grouping MSTPVLANGroupPortEntry {
    leaf MSTPVLANGroupPortEntry_PortNo {
      type int32;
    }
    leaf MSTPVLANGroupPortEntry_Tagged {
      type boolean;
    }
  }
  // core/stp/stp.proto
  grouping MSTPVLANGroupEntry {
    leaf MSTPVLANGroupEntry_VLANID {
      type int32;
    }
    container MSTPVLANGroupEntry_Ports {
      uses stppb:MSTPVLANGroupPortEntry;
    }
  }
  // core/stp/stp.proto
  grouping STPConfigBridge {
    leaf STPConfigBridge_Mode {
      type stppb:BridgeConfigModeTypeOptions;
    }
    leaf STPConfigBridge_Priority {
      type int32;
    }
    leaf STPConfigBridge_HelloTime {
      type int32;
    }
    leaf STPConfigBridge_MaxAge {
      type int32;
    }
    leaf STPConfigBridge_ForwardDelay {
      type int32;
    }
    leaf STPConfigBridge_TxHoldCount {
      type int32;
    }
    leaf STPConfigBridge_MSTPRegionName {
      type string;
    }
    leaf STPConfigBridge_MSTPRevisionLevel {
      type int32;
    }
    leaf STPConfigBridge_MSTPMaxHops {
      type int32;
    }
  }
  // core/stp/stp.proto
  grouping STPConfigPortEntry {
    leaf STPConfigPortEntry_PortNo {
      type int32;
    }
    leaf STPConfigPortEntry_Enabled {
      type boolean;
    }
    leaf STPConfigPortEntry_Priority {
      type int32;
    }
    leaf STPConfigPortEntry_AdminP2PPort {
      type stppb:PortConfigAdminP2PPortTypeOptions;
    }
    leaf STPConfigPortEntry_AdminEdgePort {
      type boolean;
    }
    leaf STPConfigPortEntry_AdminPathCost {
      type int32;
    }
    leaf STPConfigPortEntry_MSTPDefaultPriority {
      type int32;
    }
    leaf STPConfigPortEntry_MSTPPortPriority {
      type string;
    }
    leaf STPConfigPortEntry_MSTPDefaultAdminPathCost {
      type int32;
    }
    leaf STPConfigPortEntry_MSTPPortAdminPathCost {
      type string;
    }
    leaf STPConfigPortEntry_BPDUGuard {
      type stppb:PortConfigBPDUGuardTypeOptions;
    }
  }
  // core/stp/stp.proto
  grouping STPConfigMSTPGroupEntry {
    leaf STPConfigMSTPGroupEntry_MSTPID {
      type int32;
    }
    leaf STPConfigMSTPGroupEntry_BridgePriority {
      type int32;
    }
    leaf STPConfigMSTPGroupEntry_VIDs {
      type int32;
    }
  }
  // core/stp/stp.proto
  grouping STPConfig {
    container STPConfig_Bridge {
      uses stppb:STPConfigBridge;
    }
    container STPConfig_Ports {
      uses stppb:STPConfigPortEntry;
    }
    container STPConfig_MSTPGroups {
      uses stppb:STPConfigMSTPGroupEntry;
    }
  }
  // core/stp/stp.proto
  grouping BridgeConfigMode {
    leaf BridgeConfigMode_Mode {
      type stppb:BridgeConfigModeTypeOptions;
    }
  }
  // core/stp/stp.proto
  grouping BridgeConfigPriority {
    leaf BridgeConfigPriority_Priority {
      type int32;
    }
  }
  // core/stp/stp.proto
  grouping BridgeConfigHelloTime {
    leaf BridgeConfigHelloTime_HelloTime {
      type int32;
    }
  }
  // core/stp/stp.proto
  grouping BridgeConfigMaxAge {
    leaf BridgeConfigMaxAge_MaxAge {
      type int32;
    }
  }
  // core/stp/stp.proto
  grouping BridgeConfigForwardDelay {
    leaf BridgeConfigForwardDelay_ForwardDelay {
      type int32;
    }
  }
  // core/stp/stp.proto
  grouping BridgeConfigTxHoldCount {
    leaf BridgeConfigTxHoldCount_TxHoldCount {
      type int32;
    }
  }
  // core/stp/stp.proto
  grouping BridgeConfigMSTPRegionName {
    leaf BridgeConfigMSTPRegionName_MSTPRegionName {
      type string;
    }
  }
  // core/stp/stp.proto
  grouping BridgeConfigMSTPRevisionLevel {
    leaf BridgeConfigMSTPRevisionLevel_MSTPRevisionLevel {
      type int32;
    }
  }
  // core/stp/stp.proto
  grouping BridgeConfigMSTPMaxHops {
    leaf BridgeConfigMSTPMaxHops_MSTPMaxHops {
      type int32;
    }
  }
  // core/stp/stp.proto
  grouping STPPortConfigEnabledEntry {
    leaf STPPortConfigEnabledEntry_PortNo {
      type int32;
    }
    leaf STPPortConfigEnabledEntry_Enabled {
      type boolean;
    }
  }
  // core/stp/stp.proto
  grouping STPPortConfigEnabled {
    container STPPortConfigEnabled_List {
      uses stppb:STPPortConfigEnabledEntry;
    }
  }
  // core/stp/stp.proto
  grouping STPPortConfigPriorityEntry {
    leaf STPPortConfigPriorityEntry_PortNo {
      type int32;
    }
    leaf STPPortConfigPriorityEntry_Priority {
      type int32;
    }
  }
  // core/stp/stp.proto
  grouping STPPortConfigPriority {
    container STPPortConfigPriority_List {
      uses stppb:STPPortConfigPriorityEntry;
    }
  }
  // core/stp/stp.proto
  grouping STPPortConfigAdminP2PPortEntry {
    leaf STPPortConfigAdminP2PPortEntry_PortNo {
      type int32;
    }
    leaf STPPortConfigAdminP2PPortEntry_AdminP2PPort {
      type stppb:PortConfigAdminP2PPortTypeOptions;
    }
  }
  // core/stp/stp.proto
  grouping STPPortConfigAdminP2PPort {
    container STPPortConfigAdminP2PPort_List {
      uses stppb:STPPortConfigAdminP2PPortEntry;
    }
  }
  // core/stp/stp.proto
  grouping STPPortConfigAdminEdgePortEntry {
    leaf STPPortConfigAdminEdgePortEntry_PortNo {
      type int32;
    }
    leaf STPPortConfigAdminEdgePortEntry_AdminEdgePort {
      type boolean;
    }
  }
  // core/stp/stp.proto
  grouping STPPortConfigAdminEdgePort {
    container STPPortConfigAdminEdgePort_List {
      uses stppb:STPPortConfigAdminEdgePortEntry;
    }
  }
  // core/stp/stp.proto
  grouping STPPortConfigAdminPathCostEntry {
    leaf STPPortConfigAdminPathCostEntry_PortNo {
      type int32;
    }
    leaf STPPortConfigAdminPathCostEntry_AdminPathCost {
      type int32;
    }
  }
  // core/stp/stp.proto
  grouping STPPortConfigAdminPathCost {
    container STPPortConfigAdminPathCost_List {
      uses stppb:STPPortConfigAdminPathCostEntry;
    }
  }
  // core/stp/stp.proto
  grouping STPPortConfigMSTPDefaultPriorityEntry {
    leaf STPPortConfigMSTPDefaultPriorityEntry_PortNo {
      type int32;
    }
    leaf STPPortConfigMSTPDefaultPriorityEntry_MSTPDefaultPriority {
      type int32;
    }
  }
  // core/stp/stp.proto
  grouping STPPortConfigMSTPDefaultPriority {
    container STPPortConfigMSTPDefaultPriority_List {
      uses stppb:STPPortConfigMSTPDefaultPriorityEntry;
    }
  }
  // core/stp/stp.proto
  grouping STPPortConfigMSTPPortPriorityEntry {
    leaf STPPortConfigMSTPPortPriorityEntry_PortNo {
      type int32;
    }
    leaf STPPortConfigMSTPPortPriorityEntry_MSTPPortPriority {
      type string;
    }
  }
  // core/stp/stp.proto
  grouping STPPortConfigMSTPPortPriority {
    container STPPortConfigMSTPPortPriority_List {
      uses stppb:STPPortConfigMSTPPortPriorityEntry;
    }
  }
  // core/stp/stp.proto
  grouping STPPortConfigMSTPDefaultAdminPathCostEntry {
    leaf STPPortConfigMSTPDefaultAdminPathCostEntry_PortNo {
      type int32;
    }
    leaf STPPortConfigMSTPDefaultAdminPathCostEntry_MSTPDefaultAdminPathCost {
      type int32;
    }
  }
  // core/stp/stp.proto
  grouping STPPortConfigMSTPDefaultAdminPathCost {
    container STPPortConfigMSTPDefaultAdminPathCost_List {
      uses stppb:STPPortConfigMSTPDefaultAdminPathCostEntry;
    }
  }
  // core/stp/stp.proto
  grouping STPPortConfigMSTPPortAdminPathCostEntry {
    leaf STPPortConfigMSTPPortAdminPathCostEntry_PortNo {
      type int32;
    }
    leaf STPPortConfigMSTPPortAdminPathCostEntry_MSTPPortAdminPathCost {
      type string;
    }
  }
  // core/stp/stp.proto
  grouping STPPortConfigMSTPPortAdminPathCost {
    container STPPortConfigMSTPPortAdminPathCost_List {
      uses stppb:STPPortConfigMSTPPortAdminPathCostEntry;
    }
  }
  // core/stp/stp.proto
  grouping STPPortConfigBPDUGuardEntry {
    leaf STPPortConfigBPDUGuardEntry_PortNo {
      type int32;
    }
    leaf STPPortConfigBPDUGuardEntry_BPDUGuard {
      type stppb:PortConfigBPDUGuardTypeOptions;
    }
  }
  // core/stp/stp.proto
  grouping STPPortConfigBPDUGuard {
    container STPPortConfigBPDUGuard_List {
      uses stppb:STPPortConfigBPDUGuardEntry;
    }
  }
  // core/stp/stp.proto
  grouping STPPortConfigBPDUReceiveOnlyEntry {
    leaf STPPortConfigBPDUReceiveOnlyEntry_PortNo {
      type int32;
    }
    leaf STPPortConfigBPDUReceiveOnlyEntry_BPDUReceiveOnly {
      type boolean;
    }
  }
  // core/stp/stp.proto
  grouping STPPortConfigBPDUReceiveOnly {
    container STPPortConfigBPDUReceiveOnly_List {
      uses stppb:STPPortConfigBPDUReceiveOnlyEntry;
    }
  }
  // core/stp/stp.proto
  grouping STPPortConfigRestrictTcnEntry {
    leaf STPPortConfigRestrictTcnEntry_PortNo {
      type int32;
    }
    leaf STPPortConfigRestrictTcnEntry_RestrictTcn {
      type boolean;
    }
  }
  // core/stp/stp.proto
  grouping STPPortConfigRestrictTcn {
    container STPPortConfigRestrictTcn_List {
      uses stppb:STPPortConfigRestrictTcnEntry;
    }
  }
  // core/stp/stp.proto
  grouping STPPortConfigRestrictRootEntry {
    leaf STPPortConfigRestrictRootEntry_PortNo {
      type int32;
    }
    leaf STPPortConfigRestrictRootEntry_RestrictRoot {
      type boolean;
    }
  }
  // core/stp/stp.proto
  grouping STPPortConfigRestrictRoot {
    container STPPortConfigRestrictRoot_List {
      uses stppb:STPPortConfigRestrictRootEntry;
    }
  }
  // core/stp/stp.proto
  grouping MSTPIDList {
    leaf MSTPIDList_IDList {
      type int32;
    }
  }
  // core/stp/stp.proto
  grouping STPMSTPGroupEntry {
    leaf STPMSTPGroupEntry_MSTPID {
      type int32;
    }
    leaf STPMSTPGroupEntry_BridgePriority {
      type int32;
    }
    leaf STPMSTPGroupEntry_VIDs {
      type int32;
    }
  }
  // core/stp/stp.proto
  grouping MSTPGroup {
    container MSTPGroup_List {
      uses stppb:STPMSTPGroupEntry;
    }
  }
}
