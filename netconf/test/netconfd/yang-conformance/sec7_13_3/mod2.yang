module mod2 {
  yang-version 1.1;


  namespace "http://yuma123.org/ns/sec7_13_3/mod2";
  prefix m2;

  import mod1 {
    prefix m1;
  }

  organization
    "yuma123.org";



  description 'sec7_13_3 The "uses" Statement - XML Encoding Rules.';

  revision 2018-04-13 {
    description
      "Initial version";
  }

  container top2 {
    container inline {
      uses m1:foo-bar-ref-inline;
    }
  }
}
