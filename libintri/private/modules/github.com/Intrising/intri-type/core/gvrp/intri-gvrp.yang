// Code generated by protoc-gen-yang. DO NOT EDIT.


/* ****************************************************************************************************
 * Import Path : "github.com/Intrising/intri-type/core/gvrp"                                          *
 * Dir Path    : github.com/Intrising/intri-type/core/gvrp                                            *
 * Go Package  : gvrp                                                                                 *
 * Files       : 3                                                                                    *
 **************************************************************************************************** */
module intri-gvrp {

  namespace "intri:intri-gvrp";

  prefix "intri-gvrp";

  organization "Intrising Inc.";

  contact "intrising@intrising.com.tw";

  revision 2022-06-23 {
    description "Build date.";
  }

  import intri-device {
    prefix intri-device;
  }
  import intri-empty {
    prefix intri-empty;
  }
  import intri-common {
    prefix intri-common;
  }


  /* **************************************************************************************************
   * Enums       : 1                                                                                  *
   ************************************************************************************************** */
  /* core/gvrp/common.proto */
  typedef PortModeTypeOptions {
    type enumeration {
      enum PORT_MODE_NORMAL {
        description "[Normal] this mode can register/deregister static/dynamic VLAN dynamically";
        value 0;
      }
      enum PORT_MODE_FIXED {
        description "[Fixed] this mode cannot register/deregister VLAN dynamically, only share static VLAN information";
        value 1;
      }
      enum PORT_MODE_FORBIDDEN {
        description "[Forbidden] this mode cannot register/deregister VLAN dynamically, onle share default VLAN information";
        value 2;
      }
    }
  }


  /* **************************************************************************************************
   * Msgs        : 3                                                                                  *
   ************************************************************************************************** */
  /* core/gvrp/gvrp.proto */
  grouping PortConfigEntry {
    container IdentifyNo {
      uses intri-device:InterfaceIdentify;
    }
    leaf IsEnabled {
      type boolean;
    }
    leaf Mode {
      type PortModeTypeOptions;
    }
    leaf LeaveAllTimerInterval {
      type int32;
    }
    leaf JoinTimerInterval {
      type int32;
    }
    leaf HoldTimerInterval {
      type int32;
    }
    leaf LeaveTimerInterval {
      type int32;
    }
  }
  /* core/gvrp/gvrp.proto */
  grouping PortsConfig {
    container List {
      list List_Entry {
        uses PortConfigEntry;
      }
    }
  }
  /* core/gvrp/gvrp.proto */
  grouping Config {
    leaf IsEnabled {
      type boolean;
    }
    container PortsConfig {
      uses PortsConfig;
    }
  }


  /* **************************************************************************************************
   * Services    : 1                                                                                  *
   ************************************************************************************************** */

  /* **************************************************************************************************
   * Service     : GVRP                                                                               *
   * Methods     : 6                                                                                  *
   ************************************************************************************************** */
  /* core/gvrp/service.proto */
  rpc intri-gvrp-GetConfig {
    output  {
      uses Config;
    }
  }
  /* core/gvrp/service.proto */
  rpc intri-gvrp-SetGVRPEnabled {
    input  {
      uses intri-common:Enabled;
    }
  }
  /* core/gvrp/service.proto */
  rpc intri-gvrp-GetGVRPEnabled {
    output  {
      uses intri-common:Enabled;
    }
  }
  /* core/gvrp/service.proto */
  rpc intri-gvrp-GetPortsConfig {
    output  {
      uses PortsConfig;
    }
  }
  /* core/gvrp/service.proto */
  rpc intri-gvrp-UpdatePortsConfig {
    input  {
      uses PortsConfig;
    }
  }
  /* core/gvrp/service.proto */
  rpc intri-gvrp-UpdatePortConfigEntry {
    input  {
      uses PortConfigEntry;
    }
  }

}
