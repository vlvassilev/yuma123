module netconf-state {

    namespace "urn:ietf:params:xml:ns:netconf:state:1.0";
    prefix "ns";

    import yang-types { prefix yang; }
    import inet-types { prefix inet; }

    organization
        "IETF";

    description
        "NetConf Monitoring Schema.
         All elements in this Schema are read-only.";

    revision "2008-02-27" {
        description
          "Updated to match draft-ietf-netconf-monitoring-01";
    }
    revision "2008-02-01" {
        description
          "Updated to match draft-bjorklund-netconf-yang-01";
    }
    revision "2007-11-12" {
        description
        "Updated to match draft-scott-netconf-monitoring-00.txt";
    }
    revision "2007-07-22" {
        description "Initial revision.";
    }

    typedef SessionId {
        type uint32 {
            range "1..4294967295";
        }
        reference "rfc4741";
    }

    typedef ConfigName {
        type enumeration {
            enum "running";
            enum "candidate";
            enum "startup";
        }
        reference "rfc4741";
    }

    grouping transportType { // should be used, but the draft currently uses a simple string
        choice transportType { 
            mandatory true;
            leaf "console" {type empty;}
            leaf "tcp" {type empty;}
            leaf "ssh" {type empty;}
            leaf "ssl" {type empty;}
        }
    }

    grouping sessionType { // should be used, but the draft currently uses a simple string
        choice sessionType { 
            mandatory true;
            leaf "cli" {type empty;}
            leaf "netconf" {type empty;}
            leaf "webui" {type empty;}
        }
    }

    typedef srcIdentifier {
        description 
        "Information about source of the session.
        IPv4Address, IPv6Address, DNS name or any other form is allowed";
        type union {
            type inet:ipv4-address;
            type inet:ipv6-address;
            type inet:domain-name;
            type string ;
           }
    }

    container netconfState {
        config false;

        container capabilities {
            description 
                "List of NETCONF capabilities supported
                 by this device.";
            leaf-list capability {
                type yang:uri;
                min-elements 1;
            }
        }

        container sessions {
            description
                "List of NETCONF sessions currently
                 active on this device.";
            list session {
                key sessionId;
                leaf sessionId { type SessionId; }
                leaf username  { type string; }
                  leaf transport { type string; }
                leaf protocol  { type string; }
                leaf sourceIdentifier { type srcIdentifier; }
                leaf loginTime { type yang:date-and-time; }
            }
        }

        container configurations {
            description
                "List of NETCONF configuration datastores (e.g. running,
                 startup, candidate) supported on this device and related
                 information.";
            list config {
                key name;
                leaf name { type ConfigName; }
                container lockStatus {
                    description
                        "An indication of whether a resource is locked or
                         unlocked.  If locked, additional information about
                         the locking such as user an time stamp is provided.";
                    leaf lock-state {
                        type enumeration {
                            enum "locked";
                            enum "unlocked";
                        }
                    }
                    leaf lockedBySession {
                        type SessionId;
                        description 
                            "The session ID of the session that has locked
                             this resource.";
                    }
                    leaf lockedTime {
                        type yang:date-and-time;
                        description
                            "The date and time of when the resource was
                             locked. If the resource is currently unlocked,
                             this element will not be present.";
                    }
                }
            }

            container subscriptions {
                description
                    "List of NETCONF notification subscriptions
                     active on this device and related information.";
                list subscription {
                    key session-id;
                    description
                        "Information about Netconf Notification Subscriptions.";
                    leaf session-id {
                        type SessionId;
                        description
                            "The session id associated with this subscription.";
                    }
                    leaf stream {
                        type string;
                        description
                            "The stream associated with this subscription.";
                    }
                    anyxml filter {
                        description 
                            "The filters associated with this subscription.";
                    }
                    leaf messagesSent {
                        type yang:zero-based-counter32;
                        description
                            "A count of event notifications sent along
                             this connection since the subscription was
                             created.";
                    }
                }
            }
        }
    }
}
