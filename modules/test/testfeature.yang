module testfeature {

    namespace "urn:ietf:params:xml:ns:yang:testfeature";
    prefix "tf";

    revision 2008-12-02 {
        description "Initial revision.";
    }

    feature A { if-feature B; }
    feature B { if-feature C; }
    feature C { if-feature A; }
    feature D { if-feature B; }
    feature E;
}
