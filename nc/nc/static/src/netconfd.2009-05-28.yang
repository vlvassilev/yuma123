module netconfd {

    namespace "http://netconfcentral.com/ns/netconfd";

    prefix "nd";

    import ncx { prefix ncx; }

    import ncxtypes { prefix nt; }

    import ncx-app-common { prefix ncxapp; }

    import ietf-inet-types { prefix inet; }

    import ietf-with-defaults { prefix wd; }

    organization  "Netconf Central";

    contact "Andy Bierman <support@netconfcentral.com>.";

    description "NCX Agent Configuration Parameters and Statistics";

    revision 2009-05-28 {
       description 
         "pre-beta1: work-in-progress version.";
    }

    revision 2008-08-01 {
       description "Initial conversion from netconfd.ncx v 0.6";
    }

    grouping StartupChoice {
      choice start {
        description "select startup config for boot load";
        // default is set in the agt_profile

        leaf no-startup {
          description
             "If present, do not load the startup config file.";
          type empty;
        }

        leaf startup {
          description
             "The full filespec of the startup config file to use.
              If present, overrides the default startup config
              file name 'startup-cfg.xml',  This will also
              override the NCX_DATAPATH environement variable
              and the datapath CLI parameter, if the first
              character is the forward slash '/', indicating
              an absolute file path.";
          type string;
        }
      }
    }

    container netconfd {
      ncx:cli;

      description
         "Agent CLI for the NETCONF protocol.
          Usage:
            netconfd [parameters]";

      uses ncxapp:NcxAppCommon;

      leaf access-control {
        description
          "Controls how access control is enforced by the agent.";
        type enumeration {
           enum enforcing {
             description 
               "All configured access control rules will be
                enforced.";
           }
           enum permissive {
             description 
               "All configured access control rules will be
                enforced for write and execute requests.
                All read requests will be allowed, unless
                the requested object contains the
                'ncx:very-secure' extension.  In that case,
                all configured access control rules will
                be enforced.";
           }
           enum disabled {
             description 
               "All read, write, and execute requests will be
                allowed, unless the object contains the
                'ncx:secure' or 'ncx:very-secure' extension.
                If the 'ncx:secure' extension is in effect,
                then all configured access control rules
                will be enforced for write and execute requests.
                If the 'ncx:very-secure' extension is in effect,
                then all configured access control rules
                will be enforced for all requests.
                Use this mode with caution.";
           }
           enum off {
             description
               "All access control enforcement is disabled.
                Use this mode with extreme caution.";
           }
        }
        default enforcing;
      }

      leaf datapath {
        description
           "Internal file search path for config files.";
        type nt:NcPathList;
      }

      leaf default-style {
        description
           "Selects the type of filtering behavior the agent will
            advertise in the 'with-defaults' capability.  The agent
            will use this default handling behavior if the 
            'with-defaults' parameter is not explicitly set.";
         type wd:DefaultStyle;
         default report-all;
      }

/*
      leaf namespaces {
        description
          "XML namespace enforcement policy.";

        type enumeration {
          enum strict {
            description
              "XML namespaces will be strictly enforced, 
               and the correct namespace must be used for
               every XML attribute and element.";
          }
          enum lax {
             description
              "XML namespaces will be loosely enforced, 
               and a missing namespace (i.e., set to NULL
               or the NETCONF namespace) will cause the agent
               to attempt ro match the element or attribute name to
               one within a valid data model namespace.
               If multiple matches would occur, the agent
               will pick one, based on the order modules
               were initially loaded into agent.";
          }
        }
        default lax;
      }
*/

      leaf-list port {
        max-elements 4;
        description 
          "Specify the TCP ports that the agent will accept
           connections from.  These ports must also be configured
           in the /etc/ssh/sshd_config file for the SSH master
           agent to accept the connection and invoke the netconf
           subsystem.

           Up to 4 port numbers can be configured.

           If any ports are configured, then only those values
           will be accepted by the agent.

           If no ports are configured, then the agent will accept
           connections on the netconf-ssh port (tcp/830).";

         type inet:port-number;
      }

      leaf runpath {
        description
           "Internal file search path for executable modules.";
        type nt:NcPathList;
      }

      uses StartupChoice;

      leaf superuser {
        description
          "The user name to use as the superuser account.
           Any session associated with this user name 
           will bypass all access control enforcement.
           See nacm.yang for more details.

           To disable the superuser account completely,
           set this parameter to the empty string.";
        type union {
            type nt:NcxName;
            type string { length 0; }
        }
        default "superuser";
      }

      leaf target {
        description
          "The database to use as the target of edit-config
           operations.";
        type enumeration {
          enum running {
            description 
             "Write to the running config.
              Also use distinct startup capability.
              A copy-config operation must be used to 
              save the running config to the startup config file.";
          }
          enum candidate {
            description 
              "Write to the candidate config.
               Also automatically update the startup config
               file after each 'commit' operation is
               successfully completed.";
          }
        }
        // default is set in the agt_profile
        default candidate;
      }

      leaf xmlorder {
        description
          "If present, then XML element order will be enforced.
           Otherwise, XML element order errors will not be
           generated if possible. Default is no enforcement of
           strict XML order.";
        type empty;
      }

    }

    rpc load-config {
      description 
        "NCX internal load-config operation.
         The config database can be loaded dynamically
         only if the startup config phase was skipped
         via the 'no-startup' option.

         An operation-failed error will be returned and
         any startup config file was loaded (even partially)
         successfully.";

      input {
        container config {
          ncx:root;
          description "XML Config contents.";
        }
      }
    }

    rpc load {
      description 
        "Load a module into the agent, if it is not already loaded.
         Returns the module revision date (or today's date if none),
         of the module that was loaded, or an error if not found
         or the module found had errors and was not loaded
         successfully.  If the module is already loaded, then the
         revision date will simply be returned.";

      input {
        leaf module {
          description "Name of the module to load.";
          mandatory true;
          type nt:NcxName;
        }
      }

      output {
        leaf mod-revision {
          description  
            "Revision date of the module in use by the agent.
             Will only be present if the module has a version";
          type string {
            pattern '\d{4}-\d{2}-\d{2}';
          }
        }
      }

    }

    rpc restart {
      description 
        "Restart the agent. Does not reload the software image..";
      ncx:secure;
    }

    rpc shutdown {
      description 
        "Shutdown the agent.";
      ncx:secure;
    }

}
