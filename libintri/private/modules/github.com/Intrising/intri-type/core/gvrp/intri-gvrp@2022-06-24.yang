module intri-gvrp {

  namespace "intri:intri-gvrp";
  prefix "intri-gvrp";
  organization "
    Intrising Inc.";
  contact "
    intrising@intrising.com.tw";
  revision 2022-06-24 {
    description "Build date.";
  }

  import intri-device {
    prefix intri-device;
  }
  import intri-empty {
    prefix intri-empty;
  }
  import intri-common {
    prefix intri-common;
  }
  typedef PortModeTypeOptions {
    type enumeration {
      enum PORT_MODE_NORMAL {
        description "[Normal] this mode can register/deregister static/dynamic VLAN dynamically";
        value 0;
      }
      enum PORT_MODE_FIXED {
        description "[Fixed] this mode cannot register/deregister VLAN dynamically, only share static VLAN information";
        value 1;
      }
      enum PORT_MODE_FORBIDDEN {
        description "[Forbidden] this mode cannot register/deregister VLAN dynamically, onle share default VLAN information";
        value 2;
      }
    }
  }
  grouping PortConfigEntry {
    container IdentifyNo {
      uses intri-device:InterfaceIdentify;
    }
    leaf IsEnabled {
      mandatory "true";
      type boolean;
    }
    leaf Mode {
      mandatory "true";
      type PortModeTypeOptions;
    }
    leaf LeaveAllTimerInterval {
      mandatory "true";
      type int32;
    }
    leaf JoinTimerInterval {
      mandatory "true";
      type int32;
    }
    leaf HoldTimerInterval {
      mandatory "true";
      type int32;
    }
    leaf LeaveTimerInterval {
      mandatory "true";
      type int32;
    }
  }
  grouping PortsConfig {
    container List {
      list List_Entry {
        uses PortConfigEntry;
      }
    }
  }
  grouping Config {
    leaf IsEnabled {
      mandatory "true";
      type boolean;
    }
    container PortsConfig {
      uses PortsConfig;
    }
  }
  rpc intri-gvrp-GVRP-GetConfig {
    output {
      uses Config;
    }
  }
  rpc intri-gvrp-GVRP-SetGVRPEnabled {
    input {
      uses intri-common:Enabled;
    }
  }
  rpc intri-gvrp-GVRP-GetGVRPEnabled {
    output {
      uses intri-common:Enabled;
    }
  }
  rpc intri-gvrp-GVRP-GetPortsConfig {
    output {
      uses PortsConfig;
    }
  }
  rpc intri-gvrp-GVRP-UpdatePortsConfig {
    input {
      uses PortsConfig;
    }
  }
  rpc intri-gvrp-GVRP-UpdatePortConfigEntry {
    input {
      uses PortConfigEntry;
    }
  }
}
