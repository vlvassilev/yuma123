submodule intri-hardware-msg {
  belongs-to "intri-hardware" {
    prefix "intri-hardware-msg";
  }
  include intri-hardware-enum;
  import hardwarepb {
    prefix "hardwarepb";
  }
  import devicepb {
    prefix "devicepb";
  }
  import protobufpb {
    prefix "protobufpb";
  }
  import eventpb {
    prefix "eventpb";
  }
  revision 2022-06-14 {
    description "Build date.";
  }
  // hardware/common.proto
  grouping IPv4Static {
    leaf IPv4Static_IPAddress {
      type string;
    }
    leaf IPv4Static_SubnetMask {
      type string;
    }
  }
  // hardware/dldp.proto
  grouping DLDPConfig {
    container DLDPConfig_System {
      uses hardwarepb:DLDPSystemConfig;
    }
    container DLDPConfig_Port {
      uses hardwarepb:DLDPPortConfig;
    }
  }
  // hardware/dldp.proto
  grouping DLDPSystemConfig {
    leaf DLDPSystemConfig_Enabled {
      type boolean;
    }
    leaf DLDPSystemConfig_AdvertisementInterval {
      type int32;
    }
    leaf DLDPSystemConfig_ShutDownMode {
      type hardwarepb:ShutdownModeTypeOptions;
    }
    leaf DLDPSystemConfig_AuthMode {
      type hardwarepb:DLDPAuthCationModeTypeOptions;
    }
    leaf DLDPSystemConfig_WorkMode {
      type hardwarepb:DLDPWorkModeTypeOptions;
    }
  }
  // hardware/dldp.proto
  grouping DLDPPortConfig {
    container DLDPPortConfig_List {
      uses hardwarepb:DLDPPortConfigEntry;
    }
  }
  // hardware/dldp.proto
  grouping DLDPPortConfigEntry {
    container DLDPPortConfigEntry_IdentifyNo {
      uses devicepb:InterfaceIdentify;
    }
    leaf DLDPPortConfigEntry_Enabled {
      type boolean;
    }
  }
  // hardware/dldp.proto
  grouping DLDPPortStatus {
    container DLDPPortStatus_List {
      uses hardwarepb:DLDPPortStatusEntry;
    }
  }
  // hardware/dldp.proto
  grouping DLDPPortStatusEntry {
    container DLDPPortStatusEntry_IdentifyNo {
      uses devicepb:InterfaceIdentify;
    }
    leaf DLDPPortStatusEntry_Enabled {
      type boolean;
    }
    leaf DLDPPortStatusEntry_State {
      type hardwarepb:DLDPProtocolStateTypeOptions;
    }
    leaf DLDPPortStatusEntry_Link {
      type boolean;
    }
  }
  // hardware/dldp.proto
  grouping DLDPNeighborEntry {
    leaf DLDPNeighborEntry_NeighborMACAddress {
      type string;
    }
    leaf DLDPNeighborEntry_PortNo {
      type int32;
    }
    leaf DLDPNeighborEntry_NeighborAgetime {
      type int32;
    }
    leaf DLDPNeighborEntry_NeighborState {
      type hardwarepb:DLDPNeighobrStateTypeOptions;
    }
  }
  // hardware/hardware.proto
  grouping EnableRequest {
    container EnableRequest_List {
      uses hardwarepb:EnableRequestEntry;
    }
  }
  // hardware/hardware.proto
  grouping EnableRequestEntry {
    container EnableRequestEntry_IdentifyNo {
      uses devicepb:InterfaceIdentify;
    }
    leaf EnableRequestEntry_Enabled {
      type boolean;
    }
  }
  // hardware/hardware.proto
  grouping PortLED {
    container PortLED_List {
      uses hardwarepb:PortLEDEntry;
    }
  }
  // hardware/hardware.proto
  grouping PortLEDEntry {
    container PortLEDEntry_IdentifyNo {
      uses devicepb:InterfaceIdentify;
    }
    leaf PortLEDEntry_State {
      type hardwarepb:LEDBehaviorModeTypeOptions;
    }
  }
  // hardware/hardware.proto
  grouping BoardLED {
    leaf BoardLED_Power {
      type hardwarepb:LEDBehaviorModeTypeOptions;
    }
    leaf BoardLED_System {
      type hardwarepb:LEDBehaviorModeTypeOptions;
    }
    leaf BoardLED_PoEMax {
      type hardwarepb:LEDBehaviorModeTypeOptions;
    }
    leaf BoardLED_Fan {
      type hardwarepb:LEDBehaviorModeTypeOptions;
    }
    leaf BoardLED_GPS {
      type hardwarepb:LEDBehaviorModeTypeOptions;
    }
  }
  // hardware/hardware.proto
  grouping LEDStatus {
    container LEDStatus_PortLED {
      uses hardwarepb:PortLED;
    }
    container LEDStatus_SystemLED {
      uses hardwarepb:BoardLED;
    }
  }
  // hardware/hardware.proto
  grouping Coordinates {
    leaf Coordinates_Latitude {
      type string;
    }
    leaf Coordinates_Longitude {
      type string;
    }
  }
  // hardware/hardware.proto
  grouping GNSSVerboseInfomation {
    leaf GNSSVerboseInfomation_Mode {
      type string;
    }
    leaf GNSSVerboseInfomation_NavigationalStatus {
      type string;
    }
    leaf GNSSVerboseInfomation_Speed {
      type decimal64 {
        fraction-digits 2;
      }
    }
    leaf GNSSVerboseInfomation_Course {
      type decimal64 {
        fraction-digits 2;
      }
    }
    leaf GNSSVerboseInfomation_MagneticVariation {
      type decimal64 {
        fraction-digits 2;
      }
    }
  }
  // hardware/hardware.proto
  grouping GPSEnable {
    leaf GPSEnable_Enabled {
      type boolean;
    }
  }
  // hardware/hardware.proto
  grouping GPSStatus {
    leaf GPSStatus_Enabled {
      type boolean;
    }
    leaf GPSStatus_Status {
      type hardwarepb:GPSStatusTypeOptions;
    }
    container GPSStatus_VerboseInfo {
      uses hardwarepb:GNSSVerboseInfomation;
    }
    container GPSStatus_Location {
      uses hardwarepb:Coordinates;
    }
    container GPSStatus_DateTime {
      uses protobufpb:Timestamp;
    }
  }
  // hardware/hardware.proto
  grouping GPSCommand {
    leaf GPSCommand_Request {
      type string;
    }
    leaf GPSCommand_Respond {
      type string;
    }
  }
  // hardware/hardware.proto
  grouping USBStatus {
    leaf USBStatus_Enabled {
      type boolean;
    }
    leaf USBStatus_Connected {
      type boolean;
    }
    leaf USBStatus_ConnectedDevice {
      type string;
    }
  }
  // hardware/hardware.proto
  grouping USBEthernetConfig {
    container USBEthernetConfig_Static {
      uses hardwarepb:IPv4Static;
    }
  }
  // hardware/hardware.proto
  grouping FanSpeedConfig {
    container FanSpeedConfig_List {
      uses hardwarepb:FanSpeedConfigEntry;
    }
  }
  // hardware/hardware.proto
  grouping FanSpeedConfigEntry {
    leaf FanSpeedConfigEntry_FanNo {
      type int32;
    }
    leaf FanSpeedConfigEntry_RotatingSpeed {
      type int32;
    }
  }
  // hardware/hardware.proto
  grouping FanStatus {
    container FanStatus_List {
      uses hardwarepb:FanStatusEntry;
    }
  }
  // hardware/hardware.proto
  grouping FanStatusEntry {
    leaf FanStatusEntry_FanNo {
      type int32;
    }
    leaf FanStatusEntry_RotatingSpeedRPM {
      type int32;
    }
  }
  // hardware/hardware.proto
  grouping TemperatureStatus {
    container TemperatureStatus_List {
      uses hardwarepb:TemperatureStatusEntry;
    }
  }
  // hardware/hardware.proto
  grouping TemperatureStatusEntry {
    leaf TemperatureStatusEntry_Name {
      type string;
    }
    leaf TemperatureStatusEntry_ID {
      type int32;
    }
    leaf TemperatureStatusEntry_Temperature {
      type int32;
    }
  }
  // hardware/hardware.proto
  grouping PowerRedundantState {
    container PowerRedundantState_RedundantList {
      uses hardwarepb:PowerRedundantStateEntry;
    }
  }
  // hardware/hardware.proto
  grouping PowerRedundantStateEntry {
    leaf PowerRedundantStateEntry_PwOption {
      type hardwarepb:PowerRedundantTypeOptions;
    }
    leaf PowerRedundantStateEntry_PowerRedundantPlugIn {
      type boolean;
    }
    leaf PowerRedundantStateEntry_PowerRedundantACOk {
      type boolean;
    }
    leaf PowerRedundantStateEntry_PowerRedundantOk {
      type boolean;
    }
    leaf PowerRedundantStateEntry_PowerRedundantVoltage {
      type decimal64 {
        fraction-digits 2;
      }
    }
    leaf PowerRedundantStateEntry_PowerRedundantCurrent {
      type decimal64 {
        fraction-digits 2;
      }
    }
    leaf PowerRedundantStateEntry_PowerRedundantPowerConsumption {
      type decimal64 {
        fraction-digits 2;
      }
    }
    leaf PowerRedundantStateEntry_PowerRedundantTemperature {
      type decimal64 {
        fraction-digits 2;
      }
    }
  }
  // hardware/hardware.proto
  grouping PowerGeneralState {
    leaf PowerGeneralState_Power12V {
      type boolean;
    }
    leaf PowerGeneralState_Power54V {
      type boolean;
    }
  }
  // hardware/hardware.proto
  grouping PowerState {
    leaf PowerState_Type {
      type hardwarepb:PowerTypeOptions;
    }
    container PowerState_PowerRedundantState {
      uses hardwarepb:PowerRedundantState;
    }
    container PowerState_PowerGeneralState {
      uses hardwarepb:PowerGeneralState;
    }
  }
  // hardware/hardware.proto
  grouping TimeControlRegister {
    leaf TimeControlRegister_RegBase {
      type int32;
    }
    leaf TimeControlRegister_Offset {
      type int32;
    }
    leaf TimeControlRegister_Data {
      type uint8;
    }
  }
  // hardware/monitor.proto
  grouping Config {
    container Config_LED {
      uses hardwarepb:LEDConfig;
    }
    container Config_Fan {
      uses hardwarepb:FanSpeedConfig;
    }
    container Config_GPS {
      uses hardwarepb:GPSEnable;
    }
  }
  // hardware/monitor.proto
  grouping Ports {
    container Ports_List {
      uses hardwarepb:PortEntry;
    }
  }
  // hardware/monitor.proto
  grouping PortEntry {
    container PortEntry_IdentifyNo {
      uses devicepb:InterfaceIdentify;
    }
    leaf PortEntry_HardwarePortNo {
      type int32;
    }
    leaf PortEntry_SwitchPortNo {
      type int32;
    }
    leaf PortEntry_InterfaceType {
      type devicepb:PortInterfaceTypeOptions;
    }
    leaf PortEntry_Properies {
      type devicepb:PortPropertyTypeOptions;
    }
    leaf PortEntry_SupportPoE {
      type boolean;
    }
    leaf PortEntry_SupportSFP {
      type boolean;
    }
    leaf PortEntry_LinkLED {
      type hardwarepb:LEDBehaviorModeTypeOptions;
    }
    leaf PortEntry_PoELED {
      type hardwarepb:LEDBehaviorModeTypeOptions;
    }
    leaf PortEntry_SpeedLED {
      type hardwarepb:LEDBehaviorModeTypeOptions;
    }
  }
  // hardware/monitor.proto
  grouping SystemInfo {
    container SystemInfo_Fan {
      uses hardwarepb:FanPercent;
    }
    container SystemInfo_Temp {
      uses hardwarepb:TemperatureStatus;
    }
    container SystemInfo_BoardLED {
      uses hardwarepb:BoardLED;
    }
    container SystemInfo_GPS {
      uses hardwarepb:GPSStatus;
    }
  }
  // hardware/monitor.proto
  grouping LEDConfig {
    leaf LEDConfig_Mode {
      type hardwarepb:LEDModeTypeOptions;
    }
    leaf LEDConfig_ResetButton {
      type boolean;
    }
  }
  // hardware/monitor.proto
  grouping FanPercent {
    container FanPercent_List {
      uses hardwarepb:FanPercentEntry;
    }
  }
  // hardware/monitor.proto
  grouping FanPercentEntry {
    leaf FanPercentEntry_FanNo {
      type int32;
    }
    leaf FanPercentEntry_PercentRPM {
      type int32;
    }
  }
  // hardware/monitor.proto
  grouping LEDType {
    leaf LEDType_LED {
      type hardwarepb:LEDBehaviorModeTypeOptions;
    }
  }
  // hardware/monitor.proto
  grouping SignalState {
    container SignalState_List {
      uses hardwarepb:SignalStateEntry;
    }
  }
  // hardware/monitor.proto
  grouping SignalStateEntry {
    container SignalStateEntry_IdentifyNo {
      uses devicepb:InterfaceIdentify;
    }
    leaf SignalStateEntry_State {
      type boolean;
    }
  }
  // hardware/monitor.proto
  grouping SFPInfo {
    container SFPInfo_List {
      uses hardwarepb:SFPInfoEntry;
    }
  }
  // hardware/monitor.proto
  grouping SFPInfoEntry {
    container SFPInfoEntry_IdentifyNo {
      uses devicepb:InterfaceIdentify;
    }
    container SFPInfoEntry_Info {
      uses eventpb:SFPInfo;
    }
  }
  // hardware/monitor.proto
  grouping DeviceI2CAddress {
    leaf DeviceI2CAddress_Bus0 {
      type string;
    }
    leaf DeviceI2CAddress_Mux {
      type string;
    }
    container DeviceI2CAddress_List {
      uses hardwarepb:DeviceI2CAddressInfo;
    }
  }
  // hardware/monitor.proto
  grouping DeviceI2CAddressInfo {
    leaf DeviceI2CAddressInfo_Ch {
      type int32;
    }
    leaf DeviceI2CAddressInfo_Address {
      type string;
    }
  }
  // hardware/monitor.proto
  grouping InfoList {
    leaf InfoList_Info {
      type string;
    }
  }
  // hardware/monitor.proto
  grouping Enable {
    leaf Enable_Enabled {
      type boolean;
    }
  }
  // hardware/monitor.proto
  grouping Network {
    leaf Network_IP {
      type string;
    }
    leaf Network_Mask {
      type string;
    }
  }
  // hardware/monitor.proto
  grouping MCUInfo {
    container MCUInfo_List {
      uses hardwarepb:MCUVersion;
    }
  }
  // hardware/monitor.proto
  grouping MCUVersion {
    leaf MCUVersion_Name {
      type string;
    }
    leaf MCUVersion_Version {
      type string;
    }
  }
  // hardware/poe.proto
  grouping PoESetting {
    container PoESetting_List {
      uses hardwarepb:PoESettingEntry;
    }
  }
  // hardware/poe.proto
  grouping PoESettingEntry {
    container PoESettingEntry_IdentifyNo {
      uses devicepb:InterfaceIdentify;
    }
    leaf PoESettingEntry_Enable {
      type boolean;
    }
    leaf PoESettingEntry_Mode {
      type hardwarepb:PoEPortModeTypeOptions;
    }
    leaf PoESettingEntry_Priority {
      type hardwarepb:PoEPriorityLevelTypeOptions;
    }
  }
  // hardware/poe.proto
  grouping PoEPortStatusList {
    container PoEPortStatusList_List {
      uses hardwarepb:PoEPortStatusEntry;
    }
  }
  // hardware/poe.proto
  grouping PoEPortStatusEntry {
    container PoEPortStatusEntry_IdentifyNo {
      uses devicepb:InterfaceIdentify;
    }
    leaf PoEPortStatusEntry_IsEnabled {
      type boolean;
    }
    leaf PoEPortStatusEntry_IsLinkUp {
      type boolean;
    }
    leaf PoEPortStatusEntry_Class {
      type hardwarepb:PoEDeterminedClassTypeOptions;
    }
    leaf PoEPortStatusEntry_PowerConsumption {
      type decimal64 {
        fraction-digits 2;
      }
    }
    leaf PoEPortStatusEntry_Current {
      type decimal64 {
        fraction-digits 2;
      }
    }
    leaf PoEPortStatusEntry_Voltage {
      type decimal64 {
        fraction-digits 2;
      }
    }
    leaf PoEPortStatusEntry_Temperature {
      type decimal64 {
        fraction-digits 2;
      }
    }
    leaf PoEPortStatusEntry_Condition {
      type hardwarepb:PoEConditionTypeOptions;
    }
  }
  // hardware/poe.proto
  grouping PoESystemStatus {
    leaf PoESystemStatus_MinShutDownVoltage {
      type decimal64 {
        fraction-digits 2;
      }
    }
    leaf PoESystemStatus_MaxShutDownVoltage {
      type decimal64 {
        fraction-digits 2;
      }
    }
    leaf PoESystemStatus_VMainVoltage {
      type decimal64 {
        fraction-digits 2;
      }
    }
    leaf PoESystemStatus_IMainCurrent {
      type decimal64 {
        fraction-digits 2;
      }
    }
    leaf PoESystemStatus_PowerConsumption {
      type decimal64 {
        fraction-digits 2;
      }
    }
    leaf PoESystemStatus_Budget {
      type int32;
    }
    leaf PoESystemStatus_Version {
      type string;
    }
  }
  // hardware/poe.proto
  grouping PoESystemBudgetEntry {
    leaf PoESystemBudgetEntry_Budget {
      type int32;
    }
  }
}
