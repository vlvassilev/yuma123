module sercom-monitor {

  namespace "sercom:sercom-monitor";
  prefix "sercom-monitor";
  organization "
    Sercomm Inc.";
  contact "
    sercomm@sercomm.com.tw";
  revision 2022-06-24 {
    description "Build date.";
  }

  import sercom-event {
    prefix sercom-event;
  }
  import sercom-device {
    prefix sercom-device;
  }
  import sercom-empty {
    prefix sercom-empty;
  }
  typedef DeviceMonitorTypeOptions {
    type enumeration {
      enum DEVICE_MONITOR_TYPE_TEMPERATURE {
        description "[Temperature] cpu temperature";
        value 0;
      }
      enum DEVICE_MONITOR_TYPE_FAN_1 {
        description "[Fan 1] fan 1 rpm";
        value 1;
      }
      enum DEVICE_MONITOR_TYPE_FAN_2 {
        description "[Fan 2] fan 2 rpm";
        value 2;
      }
      enum DEVICE_MONITOR_TYPE_FAN_3 {
        description "[Fan 3] fan 3 rpm";
        value 3;
      }
      enum DEVICE_MONITOR_TYPE_POWER {
        description "[Power] general power voltage";
        value 10;
      }
      enum DEVICE_MONITOR_TYPE_POWER_REDUNDANT_1_TEMPERATURE {
        description "[Power Redundant 1 Temperature] power redundant 1 temperature";
        value 11;
      }
      enum DEVICE_MONITOR_TYPE_POWER_REDUNDANT_1_CURRENT {
        description "[Power Redundant 1 Current] power redundant 1 current";
        value 12;
      }
      enum DEVICE_MONITOR_TYPE_POWER_REDUNDANT_1_VOLTAGE {
        description "[Power Redundant 1 Voltage] power redundant 1 voltage";
        value 13;
      }
      enum DEVICE_MONITOR_TYPE_POWER_REDUNDANT_1_CONSUMPTION {
        description "[Power Redundant 1 Consumption] power redundant 1 consumption";
        value 14;
      }
      enum DEVICE_MONITOR_TYPE_POWER_REDUNDANT_2_TEMPERATURE {
        description "[Power Redundant 2 Temperature] power redundant 2 temperature";
        value 15;
      }
      enum DEVICE_MONITOR_TYPE_POWER_REDUNDANT_2_CURRENT {
        description "[Power Redundant 2 Current] power redundant 2 current";
        value 16;
      }
      enum DEVICE_MONITOR_TYPE_POWER_REDUNDANT_2_VOLTAGE {
        description "[Power Redundant 2 Voltage] power redundant 2 voltage";
        value 17;
      }
      enum DEVICE_MONITOR_TYPE_POWER_REDUNDANT_2_CONSUMPTION {
        description "[Power Redundant 2 Consumption] power redundant 2 consumption";
        value 18;
      }
    }
  }
  typedef SystemMonitorTypeOptions {
    type enumeration {
      enum SYSTEM_MONITOR_TYPE_CPU_UTILIZATION {
        description "[CPU] CPU utilization.";
        value 0;
      }
      enum SYSTEM_MONITOR_TYPE_MEMORY_UTILIZATION {
        description "[Memory] Memory utilization.";
        value 1;
      }
    }
  }
  typedef ValueTypeOptions {
    type enumeration {
      enum VALUE_TYPE_INT {
        description "[Int] the value is an int32.";
        value 0;
      }
      enum VALUE_TYPE_FLOAT {
        description "[float] the value is a float32.";
        value 1;
      }
      enum VALUE_TYPE_INT64 {
        description "[Int64] the value is an int64.";
        value 2;
      }
      enum VALUE_TYPE_FLOAT64 {
        description "[float64] the value is an float64.";
        value 3;
      }
    }
  }
  typedef LimitBoundaryTypeOptions {
    type enumeration {
      enum LIMIT_BOUNDARY_TYPE_NONE {
        description "[None] Has not supported the boundary settings.";
        value 0;
      }
      enum LIMIT_BOUNDARY_TYPE_INCLUDE {
        description "[Include] When the value includes the boundary will send an event.";
        value 1;
      }
      enum LIMIT_BOUNDARY_TYPE_EXCLUDE {
        description "[Exclude] When the value excludes the boundary will send an event.";
        value 2;
      }
    }
  }
  typedef HardwareLEDTypeOptions {
    type enumeration {
      enum HARDWARE_LED_TYPE_POWER {
        description "[Power]";
        value 0;
      }
      enum HARDWARE_LED_TYPE_SYSTEM {
        description "[System]";
        value 1;
      }
      enum HARDWARE_LED_TYPE_POE_MAX {
        description "[PoeMax]";
        value 2;
      }
      enum HARDWARE_LED_TYPE_FAN {
        description "[Fan]";
        value 3;
      }
      enum HARDWARE_LED_TYPE_GPS {
        description "[Gps]";
        value 4;
      }
    }
  }
  typedef LEDColorTypeOptions {
    type enumeration {
      enum LED_COLOR_TYPE_GREEN {
        description "[Green] The LED color is green.";
        value 0;
      }
      enum LED_COLOR_TYPE_RED {
        description "[Red] The LED and color is red.";
        value 1;
      }
      enum LED_COLOR_TYPE_ORANGE {
        description "[Orange] The LED and color is orange.";
        value 2;
      }
    }
  }
  typedef LEDStateTypeOptions {
    type enumeration {
      enum LED_STATE_TYPE_OFF {
        description "[Off] The LED is disabled.";
        value 0;
      }
      enum LED_STATE_TYPE_ON {
        description "[On] The LED is enabled.";
        value 1;
      }
      enum LED_STATE_TYPE_BLINKING {
        description "[Blinking] The LED is blinking.";
        value 2;
      }
    }
  }
  grouping Config {
    container DeviceLimitConfig {
      uses DeviceLimitConfig;
    }
    container SystemLimitConfig {
      uses SystemLimitConfig;
    }
  }
  grouping DeviceLimitConfigEntry {
    leaf MonitorOption {
      mandatory "true";
      type DeviceMonitorTypeOptions;
    }
    leaf LimitOption {
      mandatory "true";
      type LimitBoundaryTypeOptions;
    }
    container Boundary {
      uses RangeValue;
    }
    leaf ValueOption {
      mandatory "true";
      type ValueTypeOptions;
    }
    container Value {
      uses RangeValue;
    }
  }
  grouping DeviceLimitConfig {
    container List {
      list List_Entry {
        uses DeviceLimitConfigEntry;
      }
    }
  }
  grouping SystemLimitConfigEntry {
    leaf MonitorOption {
      mandatory "true";
      type SystemMonitorTypeOptions;
    }
    leaf LimitOption {
      mandatory "true";
      type LimitBoundaryTypeOptions;
    }
    container Boundary {
      uses RangeValue;
    }
    leaf ValueOption {
      mandatory "true";
      type ValueTypeOptions;
    }
    container Value {
      uses RangeValue;
    }
  }
  grouping SystemLimitConfig {
    container List {
      list List_Entry {
        uses SystemLimitConfigEntry;
      }
    }
  }
  grouping RangeValue {
    leaf IntMin {
      mandatory "true";
      type int32;
    }
    leaf IntMax {
      mandatory "true";
      type int32;
    }
    leaf FloatMin {
      mandatory "true";
      type decimal64 {
        fraction-digits 2;
      }
    }
    leaf FloatMax {
      mandatory "true";
      type decimal64 {
        fraction-digits 2;
      }
    }
    leaf Int64Min {
      mandatory "true";
      type int64;
    }
    leaf Int64Max {
      mandatory "true";
      type int64;
    }
    leaf Float64Min {
      mandatory "true";
      type decimal64 {
        fraction-digits 2;
      }
    }
    leaf Float64Max {
      mandatory "true";
      type decimal64 {
        fraction-digits 2;
      }
    }
  }
  grouping DeviceScorllBarValueEntry {
    leaf MonitorOption {
      mandatory "true";
      type DeviceMonitorTypeOptions;
    }
    container Value {
      uses RangeValue;
    }
  }
  grouping DeviceScorllBarValue {
    container List {
      list List_Entry {
        uses DeviceScorllBarValueEntry;
      }
    }
  }
  grouping SystemScorllBarValueEntry {
    leaf MonitorOption {
      mandatory "true";
      type SystemMonitorTypeOptions;
    }
    container Value {
      uses RangeValue;
    }
  }
  grouping SystemScorllBarValue {
    container List {
      list List_Entry {
        uses SystemScorllBarValueEntry;
      }
    }
  }
  grouping Status {
    container DeviceStatus {
      uses DeviceStatus;
    }
    container SystemStatus {
      uses SystemStatus;
    }
    container LedStatus {
      uses LEDStatus;
    }
  }
  grouping DeviceStatusEntry {
    leaf MonitorOption {
      mandatory "true";
      type DeviceMonitorTypeOptions;
    }
    container Value {
      uses DisplayValue;
    }
    leaf LoggingOption {
      mandatory "true";
      type sercom-event:LoggingTypeOptions;
    }
  }
  grouping DeviceStatus {
    container List {
      list List_Entry {
        uses DeviceStatusEntry;
      }
    }
  }
  grouping SystemStatusEntry {
    leaf MonitorOption {
      mandatory "true";
      type SystemMonitorTypeOptions;
    }
    container Value {
      uses DisplayValue;
    }
    leaf LoggingOption {
      mandatory "true";
      type sercom-event:LoggingTypeOptions;
    }
  }
  grouping SystemStatus {
    container List {
      list List_Entry {
        uses SystemStatusEntry;
      }
    }
  }
  grouping DisplayValue {
    leaf ValueUnit {
      mandatory "true";
      type string;
    }
    leaf IntValue {
      mandatory "true";
      type int32;
    }
    leaf FloatValue {
      mandatory "true";
      type decimal64 {
        fraction-digits 2;
      }
    }
    leaf Int64Value {
      mandatory "true";
      type int64;
    }
    leaf Float64Value {
      mandatory "true";
      type decimal64 {
        fraction-digits 2;
      }
    }
  }
  grouping LEDStatus {
    container SystemList {
      list SystemList_Entry {
        uses SystemLEDStatusEntry;
      }
    }
    container PortList {
      list PortList_Entry {
        uses PortLEDStatusEntry;
      }
    }
  }
  grouping SystemLEDStatusEntry {
    leaf LedType {
      mandatory "true";
      type HardwareLEDTypeOptions;
    }
    container LedState {
      uses LEDStateEntry;
    }
  }
  grouping PortLEDStatusEntry {
    container IdentifyNo {
      uses sercom-device:InterfaceIdentify;
    }
    leaf IsSfp {
      mandatory "true";
      type boolean;
    }
    container LinkLedState {
      uses LEDStateEntry;
    }
    leaf IsSupportPoELed {
      mandatory "true";
      type boolean;
    }
    container PoELedState {
      uses LEDStateEntry;
    }
    leaf IsSupportSpeedLed {
      mandatory "true";
      type boolean;
    }
    container SpeedLedState {
      uses LEDStateEntry;
    }
  }
  grouping LEDStateEntry {
    leaf StateOption {
      mandatory "true";
      type LEDStateTypeOptions;
    }
    leaf ColorOption {
      mandatory "true";
      type LEDColorTypeOptions;
    }
    leaf BlinkingIntervalMs {
      mandatory "true";
      type int32;
    }
  }
  rpc sercom-monitor-Monitor-GetConfig {
    output {
      uses Config;
    }
  }
  rpc sercom-monitor-Monitor-GetDeviceLimitConfig {
    output {
      uses DeviceLimitConfig;
    }
  }
  rpc sercom-monitor-Monitor-UpdateDeviceScorllBarValueEntry {
    input {
      uses DeviceScorllBarValueEntry;
    }
  }
  rpc sercom-monitor-Monitor-UpdateDeviceScorllBarValue {
    input {
      uses DeviceScorllBarValue;
    }
  }
  rpc sercom-monitor-Monitor-GetSystemLimitConfig {
    output {
      uses SystemLimitConfig;
    }
  }
  rpc sercom-monitor-Monitor-UpdateSystemScorllBarValueEntry {
    input {
      uses SystemScorllBarValueEntry;
    }
  }
  rpc sercom-monitor-Monitor-UpdateSystemScorllBarValue {
    input {
      uses SystemScorllBarValue;
    }
  }
  rpc sercom-monitor-Monitor-GetStatus {
    output {
      uses Status;
    }
  }
  rpc sercom-monitor-Monitor-GetDeviceStatus {
    output {
      uses DeviceStatus;
    }
  }
  rpc sercom-monitor-Monitor-GetSystemStatus {
    output {
      uses SystemStatus;
    }
  }
  rpc sercom-monitor-Monitor-GetLEDStatus {
    output {
      uses LEDStatus;
    }
  }
}
