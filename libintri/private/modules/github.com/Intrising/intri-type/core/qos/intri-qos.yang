// Code generated by protoc-gen-yang. DO NOT EDIT.


/* ****************************************************************************************************
 * Import Path : "github.com/Intrising/intri-type/core/qos"                                           *
 * Dir Path    : github.com/Intrising/intri-type/core/qos                                             *
 * Go Package  : qos                                                                                  *
 * Files       : 2                                                                                    *
 **************************************************************************************************** */
module intri-qos {

  namespace "intri:intri-qos";

  prefix "intri-qos";

  organization "Intrising Inc.";

  contact "intrising@intrising.com.tw";

  revision 2022-06-23 {
    description "Build date.";
  }

  import intri-device {
    prefix intri-device;
  }
  import intri-empty {
    prefix intri-empty;
  }


  /* **************************************************************************************************
   * Enums       : 3                                                                                  *
   ************************************************************************************************** */
  /* core/qos/qos.proto */
  typedef ModeTypeOptions {
    type enumeration {
      enum MODE_TYPE_DISABLED {
        description "[Disable] this mode has no type of traffic prioritized over another queue";
        value 0;
      }
      enum MODE_TYPE_BASIC {
        description "[Basic] this mode allows the type of traffic prioritized with the trust mode to queue";
        value 1;
      }
    }
  }
  /* core/qos/qos.proto */
  typedef TrustModeTypeOptions {
    type enumeration {
      enum TRUST_MODE_TYPE_COS {
        description "[CoS] this mode sets CoS/802.1p to queue prioritized";
        value 0;
      }
      enum TRUST_MODE_TYPE_DSCP_ONLY {
        description "[DSCP Only] this mode sets DSCP to queue prioritized";
        value 1;
      }
      enum TRUST_MODE_TYPE_DSCP_FIRST {
        description "[DSCP First] this mode sets DSCP to queue as the first priority, and then CoS to queue as the second";
        value 2;
      }
    }
  }
  /* core/qos/qos.proto */
  typedef PrioritySchemeTypeOptions {
    type enumeration {
      enum PRIORITY_SCHEME_TYPE_WRR {
        description "[WRR] WRR(Weighted Round Robin) queuing schedules all the queues, which in turn ensures every queue served for a certain time";
        value 0;
      }
      enum PRIORITY_SCHEME_TYPE_SP {
        description "[SP] SP(Strict Priority) queuing allows queue priority to reduce the response delay when congestion occurs";
        value 1;
      }
      enum PRIORITY_SCHEME_TYPE_WRR_AND_SP {
        description "[WRR+SP] WRR+SP queuing";
        value 2;
      }
    }
  }


  /* **************************************************************************************************
   * Msgs        : 12                                                                                 *
   ************************************************************************************************** */
  /* core/qos/qos.proto */
  grouping WeightedFairTrafficRatioQueueEntry {
    leaf QueueNo {
      type int32;
    }
    leaf Priority {
      type int32;
    }
    leaf Scheme {
      type PrioritySchemeTypeOptions;
    }
  }
  /* core/qos/qos.proto */
  grouping MappingCoSDot1PToQueueEntry {
    leaf CosNo {
      type int32;
    }
    leaf QueueNo {
      type int32;
    }
  }
  /* core/qos/qos.proto */
  grouping MappingDSCPToQueueEntry {
    leaf DSCPNo {
      type int32;
    }
    leaf QueueNo {
      type int32;
    }
  }
  /* core/qos/qos.proto */
  grouping InterfaceConfigEntry {
    container IdentifyNo {
      uses intri-device:InterfaceIdentify;
    }
    leaf IsEnabled {
      type boolean;
    }
    leaf EgressBandwidth {
      type int32;
    }
    leaf IngressBandwidth {
      type int32;
    }
    leaf IngressUnicastEnabled {
      type boolean;
    }
    leaf IngressMulticastEnabled {
      type boolean;
    }
    leaf IngressBroadcastEnabled {
      type boolean;
    }
  }
  /* core/qos/qos.proto */
  grouping Config {
    leaf ModeOption {
      type ModeTypeOptions;
    }
    leaf TrustModeOption {
      type TrustModeTypeOptions;
    }
    container QueueList {
      list QueueList_Entry {
        uses WeightedFairTrafficRatioQueueEntry;
      }
    }
    container CoSList {
      list CoSList_Entry {
        uses MappingCoSDot1PToQueueEntry;
      }
    }
    container DSCPList {
      list DSCPList_Entry {
        uses MappingDSCPToQueueEntry;
      }
    }
    container InterfaceList {
      list InterfaceList_Entry {
        uses InterfaceConfigEntry;
      }
    }
  }
  /* core/qos/qos.proto */
  grouping Mode {
    leaf Option {
      type ModeTypeOptions;
    }
  }
  /* core/qos/qos.proto */
  grouping TrustMode {
    leaf Option {
      type TrustModeTypeOptions;
    }
  }
  /* core/qos/qos.proto */
  grouping PriorityScheme {
    leaf Option {
      type PrioritySchemeTypeOptions;
    }
  }
  /* core/qos/qos.proto */
  grouping QueueList {
    container List {
      list List_Entry {
        uses WeightedFairTrafficRatioQueueEntry;
      }
    }
  }
  /* core/qos/qos.proto */
  grouping CoSList {
    container List {
      list List_Entry {
        uses MappingCoSDot1PToQueueEntry;
      }
    }
  }
  /* core/qos/qos.proto */
  grouping DSCPList {
    container List {
      list List_Entry {
        uses MappingDSCPToQueueEntry;
      }
    }
  }
  /* core/qos/qos.proto */
  grouping InterfaceList {
    container List {
      list List_Entry {
        uses InterfaceConfigEntry;
      }
    }
  }


  /* **************************************************************************************************
   * Services    : 1                                                                                  *
   ************************************************************************************************** */

  /* **************************************************************************************************
   * Service     : QoS                                                                                *
   * Methods     : 17                                                                                 *
   ************************************************************************************************** */
  /* core/qos/service.proto */
  rpc intri-qos-GetMode {
    output  {
      uses Mode;
    }
  }
  /* core/qos/service.proto */
  rpc intri-qos-SetMode {
    input  {
      uses Mode;
    }
  }
  /* core/qos/service.proto */
  rpc intri-qos-GetTrustMode {
    output  {
      uses TrustMode;
    }
  }
  /* core/qos/service.proto */
  rpc intri-qos-SetTrustMode {
    input  {
      uses TrustMode;
    }
  }
  /* core/qos/service.proto */
  rpc intri-qos-GetQueueList {
    output  {
      uses QueueList;
    }
  }
  /* core/qos/service.proto */
  rpc intri-qos-SetAllQueueListPriorityScheme {
    input  {
      uses PriorityScheme;
    }
  }
  /* core/qos/service.proto */
  rpc intri-qos-UpdateQueueEntry {
    input  {
      uses WeightedFairTrafficRatioQueueEntry;
    }
  }
  /* core/qos/service.proto */
  rpc intri-qos-UpdateQueueList {
    input  {
      uses QueueList;
    }
  }
  /* core/qos/service.proto */
  rpc intri-qos-GetCoSList {
    output  {
      uses CoSList;
    }
  }
  /* core/qos/service.proto */
  rpc intri-qos-UpdateCoSEntry {
    input  {
      uses MappingCoSDot1PToQueueEntry;
    }
  }
  /* core/qos/service.proto */
  rpc intri-qos-UpdateCoSList {
    input  {
      uses CoSList;
    }
  }
  /* core/qos/service.proto */
  rpc intri-qos-GetDSCPList {
    output  {
      uses DSCPList;
    }
  }
  /* core/qos/service.proto */
  rpc intri-qos-UpdateDSCPEntry {
    input  {
      uses MappingDSCPToQueueEntry;
    }
  }
  /* core/qos/service.proto */
  rpc intri-qos-UpdateDSCPList {
    input  {
      uses DSCPList;
    }
  }
  /* core/qos/service.proto */
  rpc intri-qos-GetInterfaceList {
    output  {
      uses InterfaceList;
    }
  }
  /* core/qos/service.proto */
  rpc intri-qos-UpdateInterfaceEntry {
    input  {
      uses InterfaceConfigEntry;
    }
  }
  /* core/qos/service.proto */
  rpc intri-qos-UpdateInterfaceList {
    input  {
      uses InterfaceList;
    }
  }

}
