module ncxtypes {

    yang-version 1;
    namespace "http://netconfcentral.com/ns/ncxtypes";
    prefix "nt";

    organization "Netconf Central";

    contact
        "Andy Bierman <andy at netconfcentral.com>";

    description "NCX Common Data Types";

    revision 2008-07-20 {
       description 
          "Converted from ncxtypes.ncx.";
    }

    // typedef any removed

    typedef int {
      description "Changed int base type to int32 for YANG";
      type int32;
    }

    typedef uint {
      description "Changed uint base type to uint32 for YANG";
      type uint32;
    }

    typedef long {
      description "Changed long base type to int64 for YANG";
      type int64;
    }

    typedef ulong {
      description "Changed ulong base type to uint64 for YANG";
      type uint64;
    }

    typedef ustring {
      description "Changed ustring base type to binary for YANG";
      type binary;
    }

    typedef NcxName {
        description "General Purpose NCX Name string.";
        type string {
            length "1..63";
            pattern '[a-z,A-Z][a-z,A-Z,0-9,\-,_,\.]{0,62}';
        }
    }

    typedef NcxQName {
        description 
            "Qualified Name:
              module-name:NcxName OR owner-name:NcxName.";
        type string {
            length "1..127";
            pattern '(([a-z,A-Z][a-z,A-Z,0-9,\-,_,\.]{0,62}):)' +
               '?([a-z,A-Z][a-z,A-Z,0-9,\-,_,\.]{0,62})';
        }
    }


/*
    typedef NcxVarReference {
      description
        "A variable reference string:
           $foo: try local 'foo' first, then global 'foo'
           $$foo: try only global 'foo' var";
      type string {
         length "1..63";
         pattern '$[$][a-z,A-Z][a-z,A-Z,0-9,\-,_,\.]{0,62}';
      }
    }
*/


/*
    typedef NcxScopedId {
        description "Scoped Definition Identifier string.";
        type string {
            length "3..max";
            pattern '([a-z,A-Z][a-z,A-Z,0-9,\-,_]{0,62})\.' +
              '(([a-z,A-Z][a-z,A-Z,0-9,\-,_]{0,62})+)';
        }
    }

    typedef NcxModScopedId {
        description 
            "Module Qualified Scoped Definition Identifier string.";
        type string {
            length "5..max";
            pattern '([a-z,A-Z][a-z,A-Z,0-9,\-,_]*):' +
                  '([a-z,A-Z][a-z,A-Z,0-9,\-,_]*)\.' +
                  '(([a-z,A-Z][a-z,A-Z,0-9,\-,_]*)+)';
        }
    }
*/

    typedef NcxIdentifier {
        description "Union of all the Identifier types.";
        type union { 
            type NcxName;
            type NcxQName;
        }
    }

    typedef NcxSessionId {
        description "NCX Session ID number";
        type uint32 {
            range "1..max";
        }
    }

    typedef NcxLineLength {
        description "Requested Maximum Line Length";
        type uint32 {
            range "32..65535";
        }
    }

    typedef NcxUserName {
        description "NCX User Name string.";
        type NcxName; 
    }

    typedef NcxGroupName {
        description "NCX Group Name string.";
        type NcxName;
    }

    // typedef NcxModuleList removed

    // typedef NcxLockList removed 

    typedef NcAccessControlType {
      description 
        "NCX System access control mode.";
      type enumeration {
         enum open {
            description "no access control checking enforced";
         }
         enum loose {
            description 
               "any RPC method in the netconf namespace can
                be invoked;  read-only data allowed for all";
         }
         enum strict {
            description 
              "RPC entry must be present to invoke
               an RPC method; ncxacl Data entry must be present
               to access any data. (Except for user == 'root'.)";
         }
      }
      default "strict";
    }

    typedef NcxRpcType {
        description "NCX RPC Type Classifications";
        type enumeration {
            enum other;
            enum config;
            enum exec;
            enum monitor;
            enum debug;
        }
    }

    // typedef NcxRpcTypeList removed

    typedef NcDebugType {
        description 
          "NCX Session debug logging control enumeration.
           Each successive value includes all the previous
           messages from lower value enumeration values,
           plus the messages for the specified value.

           off == no logging is done
           error == log error messages
           warn == log warning messages
           info == log info messages 
           debug == log debug level 1 messages
           debug2 == log debug level 2 messages
           debug3 == log debug level 3 messages";
        type enumeration { 
             enum off;
             enum error; 
             enum warn;
             enum info;
             enum debug;
             enum debug2;
             enum debug3;
        }
        default "info";
    }

    typedef NcPortNumber { 
        description "Transport layer port number.";
        type uint32 {
            range "1 .. 65535";
        }
    }

    typedef NcIndex { 
        description "Non-negative index value";
        type uint32 {
            range "1..max";
        }
    }

    typedef NcPathList {
      description 
        "PATHSPEC formatted string indicating the machine-dependent
         search path for the NCX programs to use.  Parameters
         with this data type can be used to override the
         default search order, and insert special work
         directories in the search path.

         Each component in the string is an absolute or
         relative directory path specification.
         The colon char ':' is used to separate the path strings.
         Whitespace is not allowed in the string at all.

         For example, the following string contains 3 paths
         that would be used in the order given:

         /home/users/testbed1/yang:/home/users/yang:/usr/share/yang";
      type string;
    }

    typedef NcModuleSpec {
      description 
        "A string which specifices a module name, or a filespec
         which represents a module.

         If the string is a simple identifier string, then
         it will be treated as a module name, and the search
         path will be used to find the complete filespec.

         If the string:
           -  ends in the sub-string '.yang' or '.ncx'
           -  begins with the dot character '.'
           -  contains any  or a path separator characters
         then it is considered to be a filespec, not a module
         name, and only that filespec will be used for input,
         instead of using the module search path.";
      type string;
    }

    typedef IndentType {
        description 
           "Requested indent amount.
            Only a limited range of line indent values are allowed.";
        type uint32 {
            range "0..9"; 
        }
        default "3";
    }

    typedef Timeout {
	description
	  "Number of seconds to wait for a response
	   from the NETCONF peer before declaring a timeout.
           Zero means no timeout at all.";
        type uint32;
        units seconds;
        default 30;
    }


}
