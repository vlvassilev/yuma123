module intri-maintenance {

  namespace "intri:intri-maintenance";
  prefix "intri-maintenance";
  organization "
    Intrising Inc.";
  contact "
    intrising@intrising.com.tw";
  revision 2022-06-24 {
    description "Build date.";
  }

  import intri-common {
    prefix intri-common;
  }
  import intri-empty {
    prefix intri-empty;
  }
  grouping FirmwareInfo {
    leaf Version {
      mandatory "true";
      type string;
    }
    leaf BuildDate {
      mandatory "true";
      type string;
    }
    leaf BuildNumber {
      mandatory "true";
      type string;
    }
  }
  grouping UpgradePathRequest {
    leaf Path {
      mandatory "true";
      type string;
    }
    leaf FTPSEnabled {
      mandatory "true";
      type boolean;
    }
    leaf RebootAfterAction {
      mandatory "true";
      type boolean;
    }
  }
  rpc intri-maintenance-Maintenance-RunRebootDevice {
    input {
      uses intri-common:Confirm;
    }
  }
  rpc intri-maintenance-Maintenance-RunCreateSnapshot {
    input {
      uses intri-common:ExportPathRequest;
    }
  }
  rpc intri-maintenance-Maintenance-GetCurrentFirmware {
    output {
      uses FirmwareInfo;
    }
  }
  rpc intri-maintenance-Maintenance-GetPreviousFirmware {
    output {
      uses FirmwareInfo;
    }
  }
  rpc intri-maintenance-Maintenance-RunGotoPreviousFirmware {
    input {
      uses intri-common:Confirm;
    }
  }
  rpc intri-maintenance-Maintenance-RunUpgradeFirmware {
    input {
      uses UpgradePathRequest;
    }
  }
}
