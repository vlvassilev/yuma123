// Code generated by protoc-gen-yang. DO NOT EDIT.


/* ****************************************************************************************************
 * Import Path : "github.com/Intrising/intri-type/core/port"                                          *
 * Dir Path    : github.com/Intrising/intri-type/core/port                                            *
 * Go Package  : port                                                                                 *
 * Files       : 2                                                                                    *
 **************************************************************************************************** */
module intri-port {

  namespace "intri:intri-port";

  prefix "intri-port";

  organization "Intrising Inc.";

  contact "intrising@intrising.com.tw";

  revision 2022-06-23 {
    description "Build date.";
  }

  import intri-device {
    prefix intri-device;
  }
  import intri-event {
    prefix intri-event;
  }
  import intri-stp {
    prefix intri-stp;
  }
  import intri-empty {
    prefix intri-empty;
  }


  /* **************************************************************************************************
   * Enums       : 1                                                                                  *
   ************************************************************************************************** */
  /* core/port/port.proto */
  typedef LinkStateTypeOptions {
    type enumeration {
      enum LINK_STATE_TYPE_LINK_DOWN {
        description "[Link Down] Link is not established. No communication. Ethernet LED is off";
        value 0;
      }
      enum LINK_STATE_TYPE_BLOCKING {
        description "[Blocking] Port is blocked. No communication. Ethernet LED indicates yellow.";
        value 1;
      }
      enum LINK_STATE_TYPE_LEARNING {
        description "[Learning] Port is learning MAC addresses. No communication. Ethernet LED indicates yellow.";
        value 2;
      }
      enum LINK_STATE_TYPE_FORWARDING {
        description "[Forwarding] Port is forwarding data. Ethernet LED indicates green.";
        value 3;
      }
      enum LINK_STATE_TYPE_UNAUTH_VLAN {
        description "[Unauth VLAN] Port is forwarding data on the unauthorized_vlan only. Ethernet LED indicates green.";
        value 4;
      }
    }
  }


  /* **************************************************************************************************
   * Msgs        : 16                                                                                 *
   ************************************************************************************************** */
  /* core/port/port.proto */
  grouping ConfigEntry {
    container IdentifyNo {
      uses intri-device:InterfaceIdentify;
    }
    leaf Alias {
      type string;
    }
    leaf PortOperation {
      type boolean;
    }
    leaf SpeedDuplex {
      type intri-event:PortSpeedDuplexTypeOptions;
    }
    leaf FlowControl {
      type boolean;
    }
    leaf EnergyEfficiency {
      type boolean;
    }
  }
  /* core/port/port.proto */
  grouping Config {
    container List {
      list List_Entry {
        uses ConfigEntry;
      }
    }
  }
  /* core/port/port.proto */
  grouping AliasEntry {
    container IdentifyNo {
      uses intri-device:InterfaceIdentify;
    }
    leaf Alias {
      type string;
    }
  }
  /* core/port/port.proto */
  grouping AliasConfig {
    container List {
      list List_Entry {
        uses AliasEntry;
      }
    }
  }
  /* core/port/port.proto */
  grouping OperationEntry {
    container IdentifyNo {
      uses intri-device:InterfaceIdentify;
    }
    leaf PortOperation {
      type boolean;
    }
  }
  /* core/port/port.proto */
  grouping OperationConfig {
    container List {
      list List_Entry {
        uses OperationEntry;
      }
    }
  }
  /* core/port/port.proto */
  grouping SpeedDuplexEntry {
    container IdentifyNo {
      uses intri-device:InterfaceIdentify;
    }
    leaf SpeedDuplex {
      type intri-event:PortSpeedDuplexTypeOptions;
    }
  }
  /* core/port/port.proto */
  grouping SpeedDuplexConfig {
    container List {
      list List_Entry {
        uses SpeedDuplexEntry;
      }
    }
  }
  /* core/port/port.proto */
  grouping FlowControlEntry {
    container IdentifyNo {
      uses intri-device:InterfaceIdentify;
    }
    leaf FlowControl {
      type boolean;
    }
  }
  /* core/port/port.proto */
  grouping FlowControlConfig {
    container List {
      list List_Entry {
        uses FlowControlEntry;
      }
    }
  }
  /* core/port/port.proto */
  grouping EnergyEfficiencyEntry {
    container IdentifyNo {
      uses intri-device:InterfaceIdentify;
    }
    leaf EnergyEfficiency {
      type boolean;
    }
  }
  /* core/port/port.proto */
  grouping EnergyEfficiencyConfig {
    container List {
      list List_Entry {
        uses EnergyEfficiencyEntry;
      }
    }
  }
  /* core/port/port.proto */
  grouping StatusEntry {
    container IdentifyNo {
      uses intri-device:InterfaceIdentify;
    }
    leaf Enabled {
      type boolean;
    }
    leaf LinkUp {
      type boolean;
    }
    leaf LastLinkChange {
      type string;
    }
    leaf SpeedDuplexUsed {
      type intri-event:PortSpeedDuplexTypeOptions;
    }
    leaf FlowControlUsed {
      type boolean;
    }
    leaf EEEActive {
      type boolean;
    }
    leaf LinkState {
      type intri-stp:PortStatusStateTypeOptions;
    }
  }
  /* core/port/port.proto */
  grouping Status {
    container List {
      list List_Entry {
        uses StatusEntry;
      }
    }
  }
  /* core/port/port.proto */
  grouping LgPortStatusEntry {
    container IdentifyNo {
      uses intri-device:InterfaceIdentify;
    }
    leaf LinkUp {
      type boolean;
    }
    leaf Existed {
      type boolean;
    }
    container ActiveNo {
      uses intri-device:InterfaceIdentify;
    }
    container Members {
      list Members_Entry {
        uses intri-device:InterfaceIdentify;
      }
    }
  }
  /* core/port/port.proto */
  grouping LgPortStatus {
    container List {
      list List_Entry {
        uses LgPortStatusEntry;
      }
    }
  }


  /* **************************************************************************************************
   * Services    : 1                                                                                  *
   ************************************************************************************************** */

  /* **************************************************************************************************
   * Service     : Port                                                                               *
   * Methods     : 12                                                                                 *
   ************************************************************************************************** */
  /* core/port/service.proto */
  rpc intri-port-GetConfig {
    output  {
      uses Config;
    }
  }
  /* core/port/service.proto */
  rpc intri-port-UpdateAliasConfig {
    input  {
      uses AliasConfig;
    }
  }
  /* core/port/service.proto */
  rpc intri-port-UpdateOperationConfig {
    input  {
      uses OperationConfig;
    }
  }
  /* core/port/service.proto */
  rpc intri-port-UpdateSpeedDuplexConfig {
    input  {
      uses SpeedDuplexConfig;
    }
  }
  /* core/port/service.proto */
  rpc intri-port-UpdateFlowControlConfig {
    input  {
      uses FlowControlConfig;
    }
  }
  /* core/port/service.proto */
  rpc intri-port-UpdateEnergyEfficiencyConfig {
    input  {
      uses EnergyEfficiencyConfig;
    }
  }
  /* core/port/service.proto */
  rpc intri-port-GetStatus {
    output  {
      uses Status;
    }
  }
  /* core/port/service.proto */
  rpc intri-port-RunRestartPorts {
    input  {
      uses intri-device:PortList;
    }
  }
  /* core/port/service.proto */
  rpc intri-port-GetLgStatus {
    output  {
      uses LgPortStatus;
    }
  }
  /* core/port/service.proto */
  rpc intri-port-RunEnablePort {
    input  {
      uses OperationEntry;
    }
  }
  /* core/port/service.proto */
  rpc intri-port-GetPortStatus {
    input  {
      uses intri-device:InterfaceIdentify;
    }
    output  {
      uses StatusEntry;
    }
  }
  /* core/port/service.proto */
  rpc intri-port-GetLgPortStatus {
    input  {
      uses intri-device:InterfaceIdentify;
    }
    output  {
      uses LgPortStatusEntry;
    }
  }

}
