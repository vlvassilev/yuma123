// Code generated by protoc-gen-yang. DO NOT EDIT.


/* ****************************************************************************************************
 * Import Path : "github.com/Intrising/intri-type/core/vlan"                                          *
 * Dir Path    : github.com/Intrising/intri-type/core/vlan                                            *
 * Go Package  : vlan                                                                                 *
 * Files       : 9                                                                                    *
 **************************************************************************************************** */
module intri-vlan {

  namespace "intri:intri-vlan";

  prefix "intri-vlan";

  organization "Intrising Inc.";

  contact "intrising@intrising.com.tw";

  revision 2022-06-23 {
    description "Build date.";
  }

  import intri-device {
    prefix intri-device;
  }
  import intri-empty {
    prefix intri-empty;
  }


  /* **************************************************************************************************
   * Enums       : 6                                                                                  *
   ************************************************************************************************** */
  /* core/vlan/common.proto */
  typedef StatusUsedTypeOptions {
    type enumeration {
      enum STATUS_USED_TYPE_CONFIG {
        description "[Config Usage] the VLAN is using by configuration";
        value 0;
      }
      enum STATUS_USED_TYPE_GVRP {
        description "[GVRP Usage] the VLAN is using by GVRP";
        value 1;
      }
      enum STATUS_USED_TYPE_VIA_MAC_TABLE {
        description "[Via MAC Table]";
        value 2;
      }
      enum STATUS_USED_TYPE_MAC_VIA_RADIUS {
        description "[MAC Via Radius]";
        value 3;
      }
      enum STATUS_USED_TYPE_802_1X_VIA_RADIUS {
        description "[802.1x Via Radius]";
        value 4;
      }
      enum STATUS_USED_TYPE_UNAUTHORIZED {
        description "[UnAuthorized]";
        value 5;
      }
    }
  }
  /* core/vlan/common.proto */
  typedef PortConfigVLANModeTypeOptions {
    type enumeration {
      enum PORT_CONFIG_VLAN_MODE_TYPE_ACCESS {
        description "[Access] the port interface is untagged port";
        value 0;
      }
      enum PORT_CONFIG_VLAN_MODE_TYPE_HYBRID {
        description "[Hybrid] the port interface is tagged/untagged port";
        value 1;
      }
      enum PORT_CONFIG_VLAN_MODE_TYPE_TRUNK {
        description "[Trunk] the port interface is tagged port";
        value 2;
      }
      enum PORT_CONFIG_VLAN_MODE_TYPE_QINQ_CUSTOMER {
        description "[Q-in-Q Customer] the port interface is tagged port, the overlapping VLAN IDs will be allow in Layer 2 Ethernet connection";
        value 3;
      }
      enum PORT_CONFIG_VLAN_MODE_TYPE_QINQ_PROVIDER {
        description "[Q-in-Q Provider] the port interface is tagged port, the overlapping VLAN IDs will be allow in Layer 2 Ethernet connection";
        value 4;
      }
    }
  }
  /* core/vlan/common.proto */
  typedef PortConfigQinQEtherTypeOptions {
    type enumeration {
      enum PORT_CONFIG_QINQ_ETHERTYPE_TYPE_0X_8100 {
        description "[0x8100] Normal VLAN tag usually not used for double tagged application. (801.1q)";
        value 0;
      }
      enum PORT_CONFIG_QINQ_ETHERTYPE_TYPE_0X_88A8 {
        description "[0x88A8] Standard value for 802.1ad";
        value 1;
      }
      enum PORT_CONFIG_QINQ_ETHERTYPE_TYPE_0X_9100 {
        description "[0x9100] Cisco standard value for 802.1ad";
        value 2;
      }
    }
  }
  /* core/vlan/common.proto */
  typedef ProtocolBasedEncapsulationTypeOptions {
    type enumeration {
      enum PROTOCOL_BASED_ENCAPSULATION_TYPE_ETHERNET_V2 {
        description "[Ethernet V2]";
        value 0;
      }
      enum PROTOCOL_BASED_ENCAPSULATION_TYPE_LLC {
        description "[LLC]";
        value 1;
      }
      enum PROTOCOL_BASED_ENCAPSULATION_TYPE_LLCSNAP {
        description "[LLC SNAP]";
        value 2;
      }
    }
  }
  /* core/vlan/common.proto */
  typedef IPVersionTypeOptions {
    type enumeration {
      enum IP_VERSION_TYPE_V4 {
        description "[IPv4]";
        value 0;
      }
      enum IP_VERSION_TYPE_V6 {
        description "[IPv6]";
        value 1;
      }
    }
  }
  /* core/vlan/common.proto */
  typedef AcceptFrameTypeOptions {
    type enumeration {
      enum ACCEPT_FRAME_TYPE_ALL {
        description "[ALL]";
        value 0;
      }
      enum ACCEPT_FRAME_TYPE_UNTAGGED_ONLY {
        description "[Untagged Only]";
        value 1;
      }
      enum ACCEPT_FRAME_TYPE_TAGGED_ONLY {
        description "[Tagged Only]";
        value 2;
      }
    }
  }


  /* **************************************************************************************************
   * Msgs        : 27                                                                                 *
   ************************************************************************************************** */
  /* core/vlan/mac_based.proto */
  grouping MACBasedGroupEntry {
    leaf MACAddress {
      type string;
    }
    leaf MACAddressMask {
      type string;
    }
    leaf GroupID {
      type int32;
    }
  }
  /* core/vlan/mac_based.proto */
  grouping MACBasedGroupMemberEntry {
    leaf VlanID {
      type int32;
    }
    leaf GroupID {
      type int32;
    }
    container IdentifyList {
      list IdentifyList_Entry {
        uses intri-device:InterfaceIdentify;
      }
    }
  }
  /* core/vlan/mac_based.proto */
  grouping MACBasedConfig {
    container GroupList {
      list GroupList_Entry {
        uses MACBasedGroupEntry;
      }
    }
    container GroupMemberList {
      list GroupMemberList_Entry {
        uses MACBasedGroupMemberEntry;
      }
    }
  }
  /* core/vlan/proto_based.proto */
  grouping ProtocolBasedGroupEntry {
    leaf GroupID {
      type int32;
    }
    leaf Encapsulation {
      type ProtocolBasedEncapsulationTypeOptions;
    }
    leaf Protocol {
      type string;
    }
  }
  /* core/vlan/proto_based.proto */
  grouping ProtocolBasedGroupMemberEntry {
    leaf VlanID {
      type int32;
    }
    leaf GroupID {
      type int32;
    }
    container IdentifyList {
      list IdentifyList_Entry {
        uses intri-device:InterfaceIdentify;
      }
    }
  }
  /* core/vlan/proto_based.proto */
  grouping ProtocolBasedConfig {
    container GroupList {
      list GroupList_Entry {
        uses ProtocolBasedGroupEntry;
      }
    }
    container GroupMemberList {
      list GroupMemberList_Entry {
        uses ProtocolBasedGroupMemberEntry;
      }
    }
  }
  /* core/vlan/selective_qinq.proto */
  grouping SelectiveQinQConfig {
    container List {
      list List_Entry {
        uses SelectiveQinQTranslatedEntry;
      }
    }
  }
  /* core/vlan/selective_qinq.proto */
  grouping SelectiveQinQTranslatedEntry {
    leaf SourceVlanID {
      type int32;
    }
    leaf TranslatedVlanID {
      type int32;
    }
  }
  /* core/vlan/subnet_based.proto */
  grouping SubnetBasedGroupEntry {
    leaf IPAddress {
      type string;
    }
    leaf IPAddressMask {
      type string;
    }
    leaf IPVersion {
      type IPVersionTypeOptions;
    }
    leaf GroupID {
      type int32;
    }
  }
  /* core/vlan/subnet_based.proto */
  grouping SubnetBasedGroupMemberEntry {
    leaf VlanID {
      type int32;
    }
    leaf GroupID {
      type int32;
    }
    container IdentifyList {
      list IdentifyList_Entry {
        uses intri-device:InterfaceIdentify;
      }
    }
  }
  /* core/vlan/subnet_based.proto */
  grouping SubnetBasedConfig {
    container GroupList {
      list GroupList_Entry {
        uses SubnetBasedGroupEntry;
      }
    }
    container GroupMemberList {
      list GroupMemberList_Entry {
        uses SubnetBasedGroupMemberEntry;
      }
    }
  }
  /* core/vlan/translation.proto */
  grouping MappingPort {
    container List {
      list List_Entry {
        uses MappingPortEntry;
      }
    }
  }
  /* core/vlan/translation.proto */
  grouping MappingPortEntry {
    container IdentifyNo {
      uses intri-device:InterfaceIdentify;
    }
    leaf Enabled {
      type boolean;
    }
  }
  /* core/vlan/translation.proto */
  grouping MappingConfig {
    container List {
      list List_Entry {
        uses MappingEntry;
      }
    }
    container PortList {
      list PortList_Entry {
        uses MappingPortEntry;
      }
    }
  }
  /* core/vlan/translation.proto */
  grouping MappingEntry {
    leaf SourceVlanID {
      type int32;
    }
    leaf TranslatedVlanID {
      type int32;
    }
  }
  /* core/vlan/vlan.proto */
  grouping Config {
    container Management {
      uses ManagementConfig;
    }
    container Voice {
      uses VoiceConfig;
    }
    container Ports {
      uses PortsConfig;
    }
    container Filters {
      uses FiltersConfig;
    }
    container MACBased {
      uses MACBasedConfig;
    }
    container SubnetBased {
      uses SubnetBasedConfig;
    }
    container ProtocolBased {
      uses ProtocolBasedConfig;
    }
    container Translation {
      uses MappingConfig;
    }
    container SelectiveQinQ {
      uses SelectiveQinQConfig;
    }
  }
  /* core/vlan/vlan.proto */
  grouping ManagementConfig {
    leaf ManagementVlanID {
      type int32;
    }
  }
  /* core/vlan/vlan.proto */
  grouping VoiceConfig {
    leaf VlanID {
      type int32;
    }
    leaf Prio {
      type int32;
    }
    leaf SignalPrio {
      type int32;
    }
    leaf DSCP {
      type int32;
    }
    leaf SignalDSCP {
      type int32;
    }
  }
  /* core/vlan/vlan.proto */
  grouping PortsConfig {
    container List {
      list List_Entry {
        uses PortEntry;
      }
    }
  }
  /* core/vlan/vlan.proto */
  grouping PortEntry {
    container IdentifyNo {
      uses intri-device:InterfaceIdentify;
    }
    leaf Mode {
      type PortConfigVLANModeTypeOptions;
    }
    leaf DefaultVlanID {
      type int32;
    }
    leaf UnauthorizedVlanID {
      type int32;
    }
    leaf FallBackVlanID {
      type int32;
    }
    leaf QinQEthertype {
      type PortConfigQinQEtherTypeOptions;
    }
    leaf AcceptableFrametype {
      type AcceptFrameTypeOptions;
    }
    container TaggedList {
      leaf-list TaggedList_Entry {
        type int32;
      }
    }
    container UntaggedList {
      leaf-list UntaggedList_Entry {
        type int32;
      }
    }
  }
  /* core/vlan/vlan.proto */
  grouping FiltersConfig {
    container List {
      list List_Entry {
        uses FilterEntry;
      }
    }
  }
  /* core/vlan/vlan.proto */
  grouping FilterEntry {
    leaf VlanID {
      type int32;
    }
    leaf Enabled {
      type boolean;
    }
    leaf Name {
      type string;
    }
  }
  /* core/vlan/vlan.proto */
  grouping Used {
    leaf Used {
      type StatusUsedTypeOptions;
    }
  }
  /* core/vlan/vlan.proto */
  grouping VlanPortVlanEntry {
    container IdentifyNo {
      uses intri-device:InterfaceIdentify;
    }
    leaf VlanID {
      type int32;
    }
    leaf Used {
      type StatusUsedTypeOptions;
    }
  }
  /* core/vlan/vlan.proto */
  grouping DefaultPortVlanEntry {
    container IdentifyNo {
      uses intri-device:InterfaceIdentify;
    }
    leaf DefaultVlanID {
      type int32;
    }
    leaf LastUpdateMethod {
      type StatusUsedTypeOptions;
    }
  }
  /* core/vlan/status.proto */
  grouping StatusEntry {
    leaf VlanID {
      type int32;
    }
    container TaggedList {
      list TaggedList_Entry {
        uses intri-device:InterfaceIdentify;
      }
    }
    container UntaggedList {
      list UntaggedList_Entry {
        uses intri-device:InterfaceIdentify;
      }
    }
  }
  /* core/vlan/status.proto */
  grouping StatusMapping {
    container Mapping {
      list Mapping_Entry {
        key "Key";
        unique "Key";
        leaf Key {
          type int32;
        }
        container Value {
          uses StatusEntry;
        }
      }
    }
  }


  /* **************************************************************************************************
   * Services    : 1                                                                                  *
   ************************************************************************************************** */

  /* **************************************************************************************************
   * Service     : VLAN                                                                               *
   * Methods     : 46                                                                                 *
   ************************************************************************************************** */
  /* core/vlan/service.proto */
  rpc intri-vlan-GetConfig {
    output  {
      uses Config;
    }
  }
  /* core/vlan/service.proto */
  rpc intri-vlan-GetStatus {
    input  {
      uses Used;
    }
    output  {
      uses StatusMapping;
    }
  }
  /* core/vlan/service.proto */
  rpc intri-vlan-GetManagementConfig {
    output  {
      uses ManagementConfig;
    }
  }
  /* core/vlan/service.proto */
  rpc intri-vlan-UpdateManagementConfig {
    input  {
      uses ManagementConfig;
    }
  }
  /* core/vlan/service.proto */
  rpc intri-vlan-GetVoiceConfig {
    output  {
      uses VoiceConfig;
    }
  }
  /* core/vlan/service.proto */
  rpc intri-vlan-UpdateVoiceConfig {
    input  {
      uses VoiceConfig;
    }
  }
  /* core/vlan/service.proto */
  rpc intri-vlan-GetFiltersConfig {
    output  {
      uses FiltersConfig;
    }
  }
  /* core/vlan/service.proto */
  rpc intri-vlan-AddFilter {
    input  {
      uses FilterEntry;
    }
  }
  /* core/vlan/service.proto */
  rpc intri-vlan-UpdateFilter {
    input  {
      uses FilterEntry;
    }
  }
  /* core/vlan/service.proto */
  rpc intri-vlan-DeleteFilter {
    input  {
      uses FilterEntry;
    }
  }
  /* core/vlan/service.proto */
  rpc intri-vlan-GetPortsConfig {
    output  {
      uses PortsConfig;
    }
  }
  /* core/vlan/service.proto */
  rpc intri-vlan-UpdatePortsConfig {
    input  {
      uses PortsConfig;
    }
  }
  /* core/vlan/service.proto */
  rpc intri-vlan-GetMappingConfig {
    output  {
      uses MappingConfig;
    }
  }
  /* core/vlan/service.proto */
  rpc intri-vlan-AddMapping {
    input  {
      uses MappingEntry;
    }
  }
  /* core/vlan/service.proto */
  rpc intri-vlan-DeleteMapping {
    input  {
      uses MappingEntry;
    }
  }
  /* core/vlan/service.proto */
  rpc intri-vlan-UpdateMappingPortEntry {
    input  {
      uses MappingPortEntry;
    }
  }
  /* core/vlan/service.proto */
  rpc intri-vlan-GetSelectiveQinQConfig {
    output  {
      uses SelectiveQinQConfig;
    }
  }
  /* core/vlan/service.proto */
  rpc intri-vlan-AddSelectiveQinQ {
    input  {
      uses SelectiveQinQTranslatedEntry;
    }
  }
  /* core/vlan/service.proto */
  rpc intri-vlan-UpdateSelectiveQinQ {
    input  {
      uses SelectiveQinQTranslatedEntry;
    }
  }
  /* core/vlan/service.proto */
  rpc intri-vlan-DeleteSelectiveQinQ {
    input  {
      uses SelectiveQinQTranslatedEntry;
    }
  }
  /* core/vlan/service.proto */
  rpc intri-vlan-GetProtocolBasedConfig {
    output  {
      uses ProtocolBasedConfig;
    }
  }
  /* core/vlan/service.proto */
  rpc intri-vlan-AddProtocolBasedGroup {
    input  {
      uses ProtocolBasedGroupEntry;
    }
  }
  /* core/vlan/service.proto */
  rpc intri-vlan-UpdateProtocolBasedGroup {
    input  {
      uses ProtocolBasedGroupEntry;
    }
  }
  /* core/vlan/service.proto */
  rpc intri-vlan-DeleteProtocolBasedGroup {
    input  {
      uses ProtocolBasedGroupEntry;
    }
  }
  /* core/vlan/service.proto */
  rpc intri-vlan-AddProtocolBasedGroupMember {
    input  {
      uses ProtocolBasedGroupMemberEntry;
    }
  }
  /* core/vlan/service.proto */
  rpc intri-vlan-UpdateProtocolBasedGroupMember {
    input  {
      uses ProtocolBasedGroupMemberEntry;
    }
  }
  /* core/vlan/service.proto */
  rpc intri-vlan-DeleteProtocolBasedGroupMember {
    input  {
      uses ProtocolBasedGroupMemberEntry;
    }
  }
  /* core/vlan/service.proto */
  rpc intri-vlan-GetMACBasedConfig {
    output  {
      uses MACBasedConfig;
    }
  }
  /* core/vlan/service.proto */
  rpc intri-vlan-AddMACBasedGroup {
    input  {
      uses MACBasedGroupEntry;
    }
  }
  /* core/vlan/service.proto */
  rpc intri-vlan-UpdateMACBasedGroup {
    input  {
      uses MACBasedGroupEntry;
    }
  }
  /* core/vlan/service.proto */
  rpc intri-vlan-DeleteMACBasedGroup {
    input  {
      uses MACBasedGroupEntry;
    }
  }
  /* core/vlan/service.proto */
  rpc intri-vlan-AddMACBasedGroupMember {
    input  {
      uses MACBasedGroupMemberEntry;
    }
  }
  /* core/vlan/service.proto */
  rpc intri-vlan-UpdateMACBasedGroupMember {
    input  {
      uses MACBasedGroupMemberEntry;
    }
  }
  /* core/vlan/service.proto */
  rpc intri-vlan-DeleteMACBasedGroupMember {
    input  {
      uses MACBasedGroupMemberEntry;
    }
  }
  /* core/vlan/service.proto */
  rpc intri-vlan-GetSubnetBasedConfig {
    output  {
      uses SubnetBasedConfig;
    }
  }
  /* core/vlan/service.proto */
  rpc intri-vlan-AddSubnetBasedGroup {
    input  {
      uses SubnetBasedGroupEntry;
    }
  }
  /* core/vlan/service.proto */
  rpc intri-vlan-UpdateSubnetBasedGroup {
    input  {
      uses SubnetBasedGroupEntry;
    }
  }
  /* core/vlan/service.proto */
  rpc intri-vlan-DeleteSubnetBasedGroup {
    input  {
      uses SubnetBasedGroupEntry;
    }
  }
  /* core/vlan/service.proto */
  rpc intri-vlan-AddSubnetBasedGroupMember {
    input  {
      uses SubnetBasedGroupMemberEntry;
    }
  }
  /* core/vlan/service.proto */
  rpc intri-vlan-UpdateSubnetBasedGroupMember {
    input  {
      uses SubnetBasedGroupMemberEntry;
    }
  }
  /* core/vlan/service.proto */
  rpc intri-vlan-DeleteSubnetBasedGroupMember {
    input  {
      uses SubnetBasedGroupMemberEntry;
    }
  }
  /* core/vlan/service.proto */
  rpc intri-vlan-GetManagementVlanPorts {
    output  {
      uses intri-device:PortList;
    }
  }
  /* core/vlan/service.proto */
  rpc intri-vlan-SetDefaultPortVlan {
    input  {
      uses DefaultPortVlanEntry;
    }
  }
  /* core/vlan/service.proto */
  rpc intri-vlan-ClearDefaultPortVlan {
    input  {
      uses DefaultPortVlanEntry;
    }
  }
  /* core/vlan/service.proto */
  rpc intri-vlan-UpdateVlanPortVlanStatus {
    input  {
      uses VlanPortVlanEntry;
    }
  }
  /* core/vlan/service.proto */
  rpc intri-vlan-DeleteVlanPortVlanStatus {
    input  {
      uses VlanPortVlanEntry;
    }
  }

}
