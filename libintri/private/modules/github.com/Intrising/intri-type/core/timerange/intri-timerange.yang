// Code generated by protoc-gen-yang. DO NOT EDIT.


/* ****************************************************************************************************
 * Import Path : "github.com/Intrising/intri-type/core/timerange"                                     *
 * Dir Path    : github.com/Intrising/intri-type/core/timerange                                       *
 * Go Package  : timerange                                                                            *
 * Files       : 2                                                                                    *
 **************************************************************************************************** */
module intri-timerange {

  namespace "intri:intri-timerange";

  prefix "intri-timerange";

  organization "Intrising Inc.";

  contact "intrising@intrising.com.tw";

  revision 2022-06-23 {
    description "Build date.";
  }

  import intri-timeofday {
    prefix intri-timeofday;
  }
  import intri-date {
    prefix intri-date;
  }
  import intri-dayofweek {
    prefix intri-dayofweek;
  }
  import intri-empty {
    prefix intri-empty;
  }
  import intri-common {
    prefix intri-common;
  }


  /* **************************************************************************************************
   * Enums       : 2                                                                                  *
   ************************************************************************************************** */
  /* core/timerange/timerange.proto */
  typedef CommandTypeOptions {
    type enumeration {
      enum COMMAND_TYPE_PERIODIC {
        description "[Periodic]";
        value 0;
      }
      enum COMMAND_TYPE_ABSOLUTE {
        description "[Absolute]";
        value 1;
      }
    }
  }
  /* core/timerange/timerange.proto */
  typedef PeriodicDayTypeOptions {
    type enumeration {
      enum PERIODIC_DAY_TYPE_DAYOFWEEK {
        description "[Day of the week]";
        value 0;
      }
      enum PERIODIC_DAY_TYPE_DAILY {
        description "[Daily]";
        value 1;
      }
      enum PERIODIC_DAY_TYPE_WEEKDAYS {
        description "[Weekdays]";
        value 2;
      }
      enum PERIODIC_DAY_TYPE_WEEKEND {
        description "[Weekend]";
        value 3;
      }
    }
  }


  /* **************************************************************************************************
   * Msgs        : 5                                                                                  *
   ************************************************************************************************** */
  /* core/timerange/timerange.proto */
  grouping Config {
    container List {
      list List_Entry {
        uses ConfigEntry;
      }
    }
  }
  /* core/timerange/timerange.proto */
  grouping ConfigEntry {
    leaf Name {
      type string;
    }
    leaf Enabled {
      type boolean;
    }
    leaf Command {
      type CommandTypeOptions;
    }
    container PeriodicDay {
      uses DayTime;
    }
    container StartTime {
      uses intri-timeofday:TimeOfDay;
    }
    container EndTime {
      uses intri-timeofday:TimeOfDay;
    }
    container StartDate {
      uses intri-date:Date;
    }
    container EndDate {
      uses intri-date:Date;
    }
  }
  /* core/timerange/timerange.proto */
  grouping DayTime {
    leaf PeriodicType {
      type PeriodicDayTypeOptions;
    }
    container DayOfWeekLists {
      leaf-list DayOfWeekLists_Entry {
        type intri-dayofweek:DayOfWeek;
      }
    }
  }
  /* core/timerange/timerange.proto */
  grouping EntryStatus {
    leaf Name {
      type string;
    }
    leaf IsActive {
      type boolean;
    }
  }
  /* core/timerange/timerange.proto */
  grouping Status {
    container List {
      list List_Entry {
        uses EntryStatus;
      }
    }
  }


  /* **************************************************************************************************
   * Services    : 1                                                                                  *
   ************************************************************************************************** */

  /* **************************************************************************************************
   * Service     : TimeRange                                                                          *
   * Methods     : 5                                                                                  *
   ************************************************************************************************** */
  /* core/timerange/service.proto */
  rpc intri-timerange-GetConfig {
    output  {
      uses Config;
    }
  }
  /* core/timerange/service.proto */
  rpc intri-timerange-GetStatus {
    output  {
      uses Status;
    }
  }
  /* core/timerange/service.proto */
  rpc intri-timerange-AddTimeRange {
    input  {
      uses ConfigEntry;
    }
  }
  /* core/timerange/service.proto */
  rpc intri-timerange-DeleteTimeRange {
    input  {
      uses intri-common:Name;
    }
  }
  /* core/timerange/service.proto */
  rpc intri-timerange-UpdateTimeRange {
    input  {
      uses ConfigEntry;
    }
  }

}
