submodule intri-portauthentication-enum {
  belongs-to "intri-portauthentication" {
    prefix "intri-portauthentication-enum";
  }
  revision 2022-06-14 {
    description "Build date.";
  }
  // core/portauthentication/common.proto
  typedef AuthorizationStateTypeOptions {
    type enumeration {
      enum AUTHORIZATION_STATE_TYPE_UNDEFINED {
        description "[Undefined]";
        value 0;
      }
      enum AUTHORIZATION_STATE_TYPE_DISABLED {
        description "[Disabled]";
        value 1;
      }
      enum AUTHORIZATION_STATE_TYPE_UNAUTHORIZED {
        description "[Unauthorized]";
        value 2;
      }
      enum AUTHORIZATION_STATE_TYPE_PROCESSING {
        description "[Processing]";
        value 3;
      }
      enum AUTHORIZATION_STATE_TYPE_AUTHORIZED {
        description "[Authorized]";
        value 4;
      }
      enum AUTHORIZATION_STATE_TYPE_REJECTED {
        description "[Rejected]";
        value 5;
      }
    }
  }
  // core/portauthentication/common.proto
  typedef AuthorizationModeTypeOptions {
    type enumeration {
      enum AUTHORIZATION_MODE_TYPE_ALWAYSAUTH {
        description "[Always Auth]";
        value 0;
      }
      enum AUTHORIZATION_MODE_TYPE_FORCEUNAUTH {
        description "[Force Unauth]";
        value 1;
      }
      enum AUTHORIZATION_MODE_TYPE_VIAMACTABLE {
        description "[Via MAC Table]";
        value 2;
      }
      enum AUTHORIZATION_MODE_TYPE_MACVIARADIUS {
        description "[MAC via RADIUS]";
        value 3;
      }
      enum AUTHORIZATION_MODE_TYPE_8021XVIARADIUS {
        description "[802.1X via RADIUS]";
        value 4;
      }
      enum AUTHORIZATION_MODE_TYPE_MAC8021XVIARADIUS {
        description "[MAC 802.1X via RADIUS]";
        value 5;
      }
      enum AUTHORIZATION_MODE_TYPE_8021XMACVIARADIUS {
        description "[802.1X MAC via RADIUS]";
        value 6;
      }
      enum AUTHORIZATION_MODE_TYPE_NONE {
        description "*internal";
        value 9;
      }
    }
  }
  // core/portauthentication/common.proto
  typedef UnAuthorizationModeTypeOptions {
    type enumeration {
      enum UNAUTHORIZATION_MODE_TYPE_BLOCKED {
        description "[Blocked]";
        value 0;
      }
      enum UNAUTHORIZATION_MODE_TYPE_USE_UNAUTHORIZEDVLAN {
        description "[Use Unauthorized VLAN]";
        value 1;
      }
      enum UNAUTHORIZATION_MODE_TYPE_INCOMING_BLOCKED {
        description "[Incoming Blocked]";
        value 2;
      }
    }
  }
  // core/portauthentication/common.proto
  typedef MACSpellingTypeOptions {
    type enumeration {
      enum MAC_SPELLING_TYPE_LOWERCASE {
        description "[Lowercase]";
        value 0;
      }
      enum MAC_SPELLING_TYPE_UPPERCASE {
        description "[Uppercase]";
        value 1;
      }
    }
  }
  // core/portauthentication/common.proto
  typedef MACPasswordSourceTypeOptions {
    type enumeration {
      enum MAC_PASSWORD_SOURCE_TYPE_USEMAC {
        description "[Use MAC]";
        value 0;
      }
      enum MAC_PASSWORD_SOURCE_TYPE_USEPASSWORD {
        description "[Use Password]";
        value 1;
      }
    }
  }
  // core/portauthentication/common.proto
  typedef EntryStateTypeOptions {
    type enumeration {
      enum ENTRY_STATE_TYPE_UNUSED {
        description "[Unused]";
        value 0;
      }
      enum ENTRY_STATE_TYPE_INACTIVE {
        description "[Inactive]";
        value 1;
      }
      enum ENTRY_STATE_TYPE_ACTIVE {
        description "[Active]";
        value 2;
      }
    }
  }
  // core/portauthentication/common.proto
  typedef MACTimeoutTypeOptions {
    type enumeration {
      enum MAC_TIMEOUT_TYPE_NONE {
        description "[None]";
        value 0;
      }
      enum MAC_TIMEOUT_TYPE_SLOW {
        description "[Slow]";
        value 1;
      }
    }
  }
}
