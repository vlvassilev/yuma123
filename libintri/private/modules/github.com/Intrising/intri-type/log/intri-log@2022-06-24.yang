module intri-log {

  namespace "intri:intri-log";
  prefix "intri-log";
  organization "
    Intrising Inc.";
  contact "
    intrising@intrising.com.tw";
  revision 2022-06-24 {
    description "Build date.";
  }

  import intri-event {
    prefix intri-event;
  }
  import intri-timestamp {
    prefix intri-timestamp;
  }
  import intri-empty {
    prefix intri-empty;
  }
  import intri-common {
    prefix intri-common;
  }
  typedef StorageTypeOptions {
    type enumeration {
      enum STORAGE_TYPE_FLASH {
        description "[Flash] Log file is stored in flash";
        value 0;
      }
      enum STORAGE_TYPE_RAM_DISK {
        description "[Ram Disk] Log file is stored in ram disk";
        value 1;
      }
    }
  }
  grouping Config {
    container BasicConfig {
      uses BasicConfig;
    }
    container TargetConfig {
      uses TargetConfig;
    }
    container ActionConfig {
      uses ActionConfig;
    }
  }
  grouping BasicConfig {
    leaf StorageOption {
      mandatory "true";
      type StorageTypeOptions;
    }
  }
  grouping TargetConfig {
    container List {
      list List_Entry {
        uses TargetConfigEntry;
      }
    }
  }
  grouping TargetConfigEntry {
    leaf Name {
      mandatory "true";
      type string;
    }
    leaf HostAddress {
      mandatory "true";
      type string;
    }
    leaf TargetLogType {
      mandatory "true";
      type intri-event:TargetLogTypeOptions;
    }
    leaf LoggingSeverityType {
      mandatory "true";
      type intri-event:LoggingSeverityTypeOptions;
    }
    leaf LogConfigChanges {
      mandatory "true";
      type boolean;
    }
    leaf LogDebugEventOnly {
      mandatory "true";
      type boolean;
    }
    leaf SnmpV3Username {
      mandatory "true";
      type string;
    }
    leaf SnmpTrapCommunity {
      mandatory "true";
      type string;
    }
  }
  grouping ActionConfig {
    container List {
      list List_Entry {
        uses ActionConfigEntry;
      }
    }
  }
  grouping ActionConfigEntry {
    leaf LoggingType {
      mandatory "true";
      type intri-event:LoggingTypeOptions;
    }
    leaf LoggingSeverityType {
      mandatory "true";
      type intri-event:LoggingSeverityTypeOptions;
    }
  }
  grouping Statistics {
    leaf NumberOfTargets {
      mandatory "true";
      type uint64;
    }
    leaf SyslogCounter {
      mandatory "true";
      type int32;
    }
    leaf SnmpTrapCounter {
      mandatory "true";
      type int32;
    }
    leaf SnmpInfoCounter {
      mandatory "true";
      type int32;
    }
    leaf DisplayInCliCounter {
      mandatory "true";
      type int32;
    }
  }
  grouping LogFileEntry {
    leaf LogID {
      mandatory "true";
      type uint64;
    }
    container Ts {
      uses intri-timestamp:Timestamp;
    }
    leaf LoggingType {
      mandatory "true";
      type intri-event:LoggingTypeOptions;
    }
    leaf LoggingSeverityType {
      mandatory "true";
      type intri-event:LoggingSeverityTypeOptions;
    }
    leaf Message {
      mandatory "true";
      type string;
    }
  }
  grouping LogFiles {
    container List {
      list List_Entry {
        uses LogFileEntry;
      }
    }
  }
  rpc intri-log-Log-GetConfig {
    output {
      uses Config;
    }
  }
  rpc intri-log-Log-GetBasicConfig {
    output {
      uses BasicConfig;
    }
  }
  rpc intri-log-Log-UpdateBasicConfig {
    input {
      uses BasicConfig;
    }
  }
  rpc intri-log-Log-GetTargetConfig {
    output {
      uses TargetConfig;
    }
  }
  rpc intri-log-Log-AddTargetConfigEntry {
    input {
      uses TargetConfigEntry;
    }
  }
  rpc intri-log-Log-UpdateTargetConfigEntry {
    input {
      uses TargetConfigEntry;
    }
  }
  rpc intri-log-Log-DeleteTargetConfigEntry {
    input {
      uses TargetConfigEntry;
    }
  }
  rpc intri-log-Log-GetActionConfig {
    output {
      uses ActionConfig;
    }
  }
  rpc intri-log-Log-UpdateActionConfig {
    input {
      uses ActionConfig;
    }
  }
  rpc intri-log-Log-RunSendTestEvent {
  }
  rpc intri-log-Log-GetStatistics {
    output {
      uses Statistics;
    }
  }
  rpc intri-log-Log-RunCleanStatistics {
  }
  rpc intri-log-Log-GetRecordTargetLogList {
    output {
      uses LogFiles;
    }
  }
  rpc intri-log-Log-RunCleanRecordTargetLogList {
  }
  rpc intri-log-Log-RunSaveLogToYAML {
    input {
      uses intri-common:Path;
    }
  }
}
