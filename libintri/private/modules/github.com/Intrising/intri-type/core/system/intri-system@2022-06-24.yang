module intri-system {

  namespace "intri:intri-system";
  prefix "intri-system";
  organization "
    Intrising Inc.";
  contact "
    intrising@intrising.com.tw";
  revision 2022-06-24 {
    description "Build date.";
  }

  import intri-empty {
    prefix intri-empty;
  }
  grouping Status {
    leaf LastBootTime {
      mandatory "true";
      type string;
    }
    leaf Uptime {
      mandatory "true";
      type int64;
    }
  }
  grouping Config {
    leaf SysName {
      mandatory "true";
      type string;
    }
    leaf SysLocation {
      mandatory "true";
      type string;
    }
    leaf SysGroup {
      mandatory "true";
      type string;
    }
    leaf SysContact {
      mandatory "true";
      type string;
    }
  }
  grouping IdentificationConfig {
    leaf SysName {
      mandatory "true";
      type string;
    }
    leaf SysLocation {
      mandatory "true";
      type string;
    }
    leaf SysGroup {
      mandatory "true";
      type string;
    }
    leaf SysContact {
      mandatory "true";
      type string;
    }
  }
  rpc intri-system-System-GetConfig {
    output {
      uses Config;
    }
  }
  rpc intri-system-System-SetConfig {
    input {
      uses Config;
    }
  }
  rpc intri-system-System-GetStatus {
    output {
      uses Status;
    }
  }
}
