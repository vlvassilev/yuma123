submodule intri-dhcpserver-msg {
  belongs-to "intri-dhcpserver" {
    prefix "intri-dhcpserver-msg";
  }
  include intri-dhcpserver-enum;
  import dhcpserverpb {
    prefix "dhcpserverpb";
  }
  import devicepb {
    prefix "devicepb";
  }
  revision 2022-06-14 {
    description "Build date.";
  }
  // core/dhcpserver/dhcpserver.proto
  grouping Config {
    container Config_V4 {
      uses dhcpserverpb:V4Config;
    }
  }
  // core/dhcpserver/dhcpserver.proto
  grouping V4Config {
    container V4Config_Sys {
      uses dhcpserverpb:System;
    }
    container V4Config_Pool {
      uses dhcpserverpb:Pool;
    }
  }
  // core/dhcpserver/dhcpserver.proto
  grouping System {
    leaf System_Enabled {
      type boolean;
    }
  }
  // core/dhcpserver/dhcpserver.proto
  grouping Pool {
    container Pool_List {
      uses dhcpserverpb:PoolEntry;
    }
  }
  // core/dhcpserver/dhcpserver.proto
  grouping PoolEntry {
    leaf PoolEntry_Name {
      type string;
    }
    container PoolEntry_Interface {
      uses devicepb:InterfaceIdentify;
    }
    leaf PoolEntry_EntryType {
      type dhcpserverpb:PoolTypeOptions;
    }
    container PoolEntry_Basic {
      uses dhcpserverpb:Basic;
    }
    container PoolEntry_MACBased {
      uses dhcpserverpb:MACBased;
    }
    container PoolEntry_PortBased {
      uses dhcpserverpb:PortBased;
    }
    leaf PoolEntry_ID {
      type string;
    }
  }
  // core/dhcpserver/dhcpserver.proto
  grouping Basic {
    leaf Basic_RangeLow {
      type string;
    }
    leaf Basic_RangeHigh {
      type string;
    }
    leaf Basic_Netmask {
      type string;
    }
    leaf Basic_Gateway {
      type string;
    }
    leaf Basic_PrimaryDNS {
      type string;
    }
    leaf Basic_SecondaryDNS {
      type string;
    }
    leaf Basic_LeaseTime {
      type int32;
    }
  }
  // core/dhcpserver/dhcpserver.proto
  grouping MACBased {
    leaf MACBased_MACAddress {
      type string;
    }
    leaf MACBased_DesiredIP {
      type string;
    }
  }
  // core/dhcpserver/dhcpserver.proto
  grouping PortBased {
    leaf PortBased_PortNo {
      type int32;
    }
    leaf PortBased_Ignore {
      type boolean;
    }
    leaf PortBased_DesiredIP {
      type string;
    }
  }
  // core/dhcpserver/dhcpserver.proto
  grouping StatusEntry {
    leaf StatusEntry_Name {
      type string;
    }
    container StatusEntry_Interface {
      uses devicepb:InterfaceIdentify;
    }
    leaf StatusEntry_PortNo {
      type int32;
    }
    leaf StatusEntry_MACAddress {
      type string;
    }
    leaf StatusEntry_IPAddress {
      type string;
    }
    leaf StatusEntry_AvailableLeaseTime {
      type int32;
    }
  }
  // core/dhcpserver/dhcpserver.proto
  grouping Status {
    container Status_List {
      uses dhcpserverpb:StatusEntry;
    }
  }
}
