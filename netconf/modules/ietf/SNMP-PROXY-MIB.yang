/*
 * This module has been generated by smidump 0.4.6:
 *
 *      smidump -f yang --yang-smi-extensions SNMP-PROXY-MIB
 *
 * Do not edit. Edit the source file instead!
 */

module SNMP-PROXY-MIB {

   /*** NAMESPACE / PREFIX DEFINITION ***/

   namespace "urn:ietf:params:xml:ns:yang:smiv2:SNMP-PROXY-MIB";
   prefix "snmp-proxy";

   /*** LINKAGE (IMPORTS / INCLUDES) ***/

   import SNMP-FRAMEWORK-MIB { prefix "snmp-framework"; }
   import SNMP-TARGET-MIB    { prefix "snmp-target"; }
   import SNMPv2-TC          { prefix "smiv2"; }
   import yang-smi           { prefix "smi"; }

   /*** META INFORMATION ***/

   organization     
     "IETF SNMPv3 Working Group";

   contact          
     "WG-email:   snmpv3@lists.tislabs.com
      Subscribe:  majordomo@lists.tislabs.com
                  In message body:  subscribe snmpv3
      
      Co-Chair:   Russ Mundy
                  Network Associates Laboratories
      Postal:     15204 Omega Drive, Suite 300
                  Rockville, MD 20850-4601
                  USA
      EMail:      mundy@tislabs.com
      Phone:      +1 301-947-7107
      
      Co-Chair:   David Harrington
                  Enterasys Networks
      Postal:     35 Industrial Way
                  P. O. Box 5004
                  Rochester, New Hampshire 03866-5005
                  USA
      EMail:      dbh@enterasys.com
      Phone:      +1 603-337-2614
      
      Co-editor:  David B. Levi
                  Nortel Networks
      Postal:     3505 Kesterwood Drive
                  Knoxville, Tennessee 37918
      EMail:      dlevi@nortelnetworks.com
      Phone:      +1 865 686 0432
      
      Co-editor:  Paul Meyer
                  Secure Computing Corporation
      Postal:     2675 Long Lake Road
                  Roseville, Minnesota 55113
      EMail:      paul_meyer@securecomputing.com
      Phone:      +1 651 628 1592
      
      Co-editor:  Bob Stewart
                  Retired";

   description      
     "This MIB module defines MIB objects which provide
      mechanisms to remotely configure the parameters
      used by a proxy forwarding application.
      
      Copyright (C) The Internet Society (2002). This
      version of this MIB module is part of RFC 3413;
      see the RFC itself for full legal notices.";

   revision "2002-10-14" {
      description   
        "Clarifications, published as
         RFC 3413.";
   }
   revision "1998-08-04" {
      description   
        "Clarifications, published as
         RFC 2573.";
   }
   revision "1997-07-14" {
      description   
        "The initial revision, published as RFC2273.";
   }

   container snmpProxyObjects {


      /* XXX table comments here XXX */

      list snmpProxyEntry {

         key "snmpProxyName";
         description 
           "A set of translation parameters used by a proxy forwarder
            application for forwarding SNMP messages.
            
            Entries in the snmpProxyTable are created and deleted
            using the snmpProxyRowStatus object.";
         smi:oid "1.3.6.1.6.3.14.1.2.1";


         leaf snmpProxyName {
            type snmp-framework:SnmpAdminString {
               length "1..32";
            }
            config false;
            description   
              "The locally arbitrary, but unique identifier associated
               with this snmpProxyEntry.";
            smi:oid "1.3.6.1.6.3.14.1.2.1.1";
         }

         leaf snmpProxyType {
            type enumeration {
               enum read   { value 1; }
               enum write  { value 2; }
               enum trap   { value 3; }
               enum inform { value 4; }
            }
            config true;
            description   
              "The type of message that may be forwarded using
               the translation parameters defined by this entry.";
            smi:oid "1.3.6.1.6.3.14.1.2.1.2";
         }

         leaf snmpProxyContextEngineID {
            type snmp-framework:SnmpEngineID;
            config true;
            description   
              "The contextEngineID contained in messages that
               may be forwarded using the translation parameters
               defined by this entry.";
            smi:oid "1.3.6.1.6.3.14.1.2.1.3";
         }

         leaf snmpProxyContextName {
            type snmp-framework:SnmpAdminString;
            config true;
            description   
              "The contextName contained in messages that may be
               forwarded using the translation parameters defined
               by this entry.
               
               This object is optional, and if not supported, the
               contextName contained in a message is ignored when
               selecting an entry in the snmpProxyTable.";
            smi:oid "1.3.6.1.6.3.14.1.2.1.4";
         }

         leaf snmpProxyTargetParamsIn {
            type snmp-framework:SnmpAdminString;
            config true;
            description   
              "This object selects an entry in the snmpTargetParamsTable.
               The selected entry is used to determine which row of the
               snmpProxyTable to use for forwarding received messages.";
            smi:oid "1.3.6.1.6.3.14.1.2.1.5";
         }

         leaf snmpProxySingleTargetOut {
            type snmp-framework:SnmpAdminString;
            config true;
            description   
              "This object selects a management target defined in the
               snmpTargetAddrTable (in the SNMP-TARGET-MIB).  The
               selected target is defined by an entry in the
               snmpTargetAddrTable whose index value (snmpTargetAddrName)
               is equal to this object.
               
               This object is only used when selection of a single
               target is required (i.e. when forwarding an incoming
               read or write request).";
            smi:oid "1.3.6.1.6.3.14.1.2.1.6";
         }

         leaf snmpProxyMultipleTargetOut {
            type snmp-target:SnmpTagValue;
            config true;
            description   
              "This object selects a set of management targets defined
               in the snmpTargetAddrTable (in the SNMP-TARGET-MIB).
               
               This object is only used when selection of multiple
               targets is required (i.e. when forwarding an incoming
               notification).";
            smi:oid "1.3.6.1.6.3.14.1.2.1.7";
         }

         leaf snmpProxyStorageType {
            type smiv2:StorageType;
            config true;
            description   
              "The storage type of this conceptual row.
               Conceptual rows having the value 'permanent' need not
               allow write-access to any columnar objects in the row.";
            smi:default "nonVolatile";
            smi:oid "1.3.6.1.6.3.14.1.2.1.8";
         }

         leaf snmpProxyRowStatus {
            type smiv2:RowStatus;
            config true;
            description   
              "The status of this conceptual row.
               
               To create a row in this table, a manager must
               
               set this object to either createAndGo(4) or
               createAndWait(5).
               
               The following objects may not be modified while the
               value of this object is active(1):
                   - snmpProxyType
                   - snmpProxyContextEngineID
                   - snmpProxyContextName
                   - snmpProxyTargetParamsIn
                   - snmpProxySingleTargetOut
                   - snmpProxyMultipleTargetOut";
            smi:oid "1.3.6.1.6.3.14.1.2.1.9";
         }
      }
      smi:oid "1.3.6.1.6.3.14.1";
   }

} /* end of module SNMP-PROXY-MIB */
