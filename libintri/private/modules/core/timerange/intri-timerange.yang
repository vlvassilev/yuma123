module intri-timerange {
  namespace "intri:intri-timerange";
  prefix "intri-timerange";
  import timerangepb {
    prefix "timerangepb";
  }
  organization "Intrising Inc.";
  contact "xxx@intrising.com.tw";
  revision 2022-06-14 {
    description "Build date.";
  }
}
