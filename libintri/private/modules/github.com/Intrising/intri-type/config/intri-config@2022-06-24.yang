module intri-config {

  namespace "intri:intri-config";
  prefix "intri-config";
  organization "
    Intrising Inc.";
  contact "
    intrising@intrising.com.tw";
  revision 2022-06-24 {
    description "Build date.";
  }

  import intri-acl {
    prefix intri-acl;
  }
  import intri-vlan {
    prefix intri-vlan;
  }
  import intri-gvrp {
    prefix intri-gvrp;
  }
  import intri-access {
    prefix intri-access;
  }
  import intri-userinterface {
    prefix intri-userinterface;
  }
  import intri-system {
    prefix intri-system;
  }
  import intri-network {
    prefix intri-network;
  }
  import intri-time {
    prefix intri-time;
  }
  import intri-port {
    prefix intri-port;
  }
  import intri-sfp {
    prefix intri-sfp;
  }
  import intri-mirroring {
    prefix intri-mirroring;
  }
  import intri-isolation {
    prefix intri-isolation;
  }
  import intri-fdb {
    prefix intri-fdb;
  }
  import intri-portsecurity {
    prefix intri-portsecurity;
  }
  import intri-files {
    prefix intri-files;
  }
  import intri-lacp {
    prefix intri-lacp;
  }
  import intri-multicast {
    prefix intri-multicast;
  }
  import intri-stormcontrol {
    prefix intri-stormcontrol;
  }
  import intri-dhcp {
    prefix intri-dhcp;
  }
  import intri-qos {
    prefix intri-qos;
  }
  import intri-loop {
    prefix intri-loop;
  }
  import intri-lldp {
    prefix intri-lldp;
  }
  import intri-poe {
    prefix intri-poe;
  }
  import intri-cdp {
    prefix intri-cdp;
  }
  import intri-dhcpserver {
    prefix intri-dhcpserver;
  }
  import intri-stp {
    prefix intri-stp;
  }
  import intri-timerange {
    prefix intri-timerange;
  }
  import intri-ptp {
    prefix intri-ptp;
  }
  import intri-monitor {
    prefix intri-monitor;
  }
  import intri-timesync {
    prefix intri-timesync;
  }
  import intri-udld {
    prefix intri-udld;
  }
  import intri-portauthentication {
    prefix intri-portauthentication;
  }
  import intri-log {
    prefix intri-log;
  }
  import intri-common {
    prefix intri-common;
  }
  import intri-empty {
    prefix intri-empty;
  }
  typedef StorageTypeOptions {
    type enumeration {
      enum STORAGE_TYPE_RAM_DISK {
        description "[In RAM Disk] Configuration is saved in RAM dist";
        value 0;
      }
    }
  }
  typedef SaveModeTypeOptions {
    type enumeration {
      enum SAVE_MODE_TYPE_TEMPORARILY {
        description "[Temporarily] Modification on config is temporarily before save.";
        value 0;
      }
    }
  }
  typedef ConfigTypeOptions {
    type enumeration {
      enum CONIFG_TYPE_RUNNING {
        description "[Running] Running Configuration";
        value 0;
      }
      enum CONIFG_TYPE_DEFAULT {
        description "[Default] Default Configuration";
        value 1;
      }
      enum CONIFG_TYPE_SAVE {
        description "[Save] Save Configuration";
        value 2;
      }
    }
  }
  typedef ConfigStateTypeOptions {
    type enumeration {
      enum CONFIG_STATE_TYPE_SAVED {
        description "[Saved] Configuration is saved";
        value 0;
      }
      enum CONFIG_STATE_TYPE_CHANGED {
        description "[Changed] Configuration is changed";
        value 1;
      }
    }
  }
  typedef FactoryDefaultModeTypeOptions {
    type enumeration {
      enum FACTORY_DEFAULT_MODE_TYPE_KEEP_ALL {
        description "[Keep All] Reset default but keep user/network configs";
        value 0;
      }
      enum FACTORY_DEFAULT_MODE_TYPE_KEEP_USER_ACCOUNTS {
        description "[Keep User Accounts] Reset default but keep user accounts";
        value 1;
      }
      enum FACTORY_DEFAULT_MODE_TYPE_KEEP_NETWORK_CONFIGS {
        description "[Keep Network Configs] Reset default but keep network configs";
        value 2;
      }
      enum FACTORY_DEFAULT_MODE_TYPE_RESET_ALL {
        description "[Reset All] Reset to factory default";
        value 3;
      }
    }
  }
  grouping ImportAction {
    leaf FileURL {
      mandatory "true";
      type string;
    }
    leaf RebootAfterAction {
      mandatory "true";
      type boolean;
    }
  }
  grouping ExportAction {
    leaf FileURL {
      mandatory "true";
      type string;
    }
    leaf IsFTPS {
      mandatory "true";
      type boolean;
    }
    leaf ForceTFTP {
      mandatory "true";
      type boolean;
    }
  }
  grouping SaveModeStatus {
    leaf SaveStorageOption {
      mandatory "true";
      type StorageTypeOptions;
    }
    leaf SaveModeOption {
      mandatory "true";
      type SaveModeTypeOptions;
    }
    leaf ConfigStateOption {
      mandatory "true";
      type ConfigStateTypeOptions;
    }
    leaf ConfigLastUpdated {
      mandatory "true";
      type string;
    }
  }
  grouping RestoreDefaultType {
    leaf Type {
      mandatory "true";
      type FactoryDefaultModeTypeOptions;
    }
  }
  grouping AllServicesConfig {
    container Acl {
      uses intri-acl:Config;
    }
    container Vlan {
      uses intri-vlan:Config;
    }
    container Gvrp {
      uses intri-gvrp:Config;
    }
    container Access {
      uses intri-access:Config;
    }
    container UserInterface {
      uses intri-userinterface:Config;
    }
    container System {
      uses intri-system:Config;
    }
    container Network {
      uses intri-network:Config;
    }
    container Time {
      uses intri-time:Config;
    }
    container Port {
      uses intri-port:Config;
    }
    container Sfp {
      uses intri-sfp:Config;
    }
    container Mirroring {
      uses intri-mirroring:Config;
    }
    container Isolation {
      uses intri-isolation:Config;
    }
    container Fdb {
      uses intri-fdb:Config;
    }
    container PortSecurity {
      uses intri-portsecurity:Config;
    }
    container Files {
      uses intri-files:Config;
    }
    container Lacp {
      uses intri-lacp:Config;
    }
    container Multicast {
      uses intri-multicast:Config;
    }
    container StormControl {
      uses intri-stormcontrol:Config;
    }
    container Dhcp {
      uses intri-dhcp:Config;
    }
    container QoS {
      uses intri-qos:Config;
    }
    container Loop {
      uses intri-loop:Config;
    }
    container Lldp {
      uses intri-lldp:Config;
    }
    container Poe {
      uses intri-poe:Config;
    }
    container Cdp {
      uses intri-cdp:Config;
    }
    container DhcpServer {
      uses intri-dhcpserver:Config;
    }
    container Stp {
      uses intri-stp:STPConfig;
    }
    container Mstp {
      uses intri-stp:MSTPConfig;
    }
    container TimeRange {
      uses intri-timerange:Config;
    }
    container ArpInspection {
      uses intri-dhcp:ARPInspectionConfig;
    }
    container Ptp {
      uses intri-ptp:Config;
    }
    container Monitor {
      uses intri-monitor:Config;
    }
    container TimeSync {
      uses intri-timesync:Config;
    }
    container Udld {
      uses intri-udld:Config;
    }
    container PortAuthentication {
      uses intri-portauthentication:Config;
    }
    container Log {
      uses intri-log:Config;
    }
  }
  grouping ValidateConfigResult {
    container List {
      leaf-list List_Entry {
        type string;
      }
    }
  }
  rpc intri-config-Config-RunImportConfig {
    input {
      uses intri-common:ImportPathRequest;
    }
  }
  rpc intri-config-Config-RunExportConfig {
    input {
      uses intri-common:ExportPathRequest;
    }
  }
  rpc intri-config-Config-GetSaveModeStatus {
    output {
      uses SaveModeStatus;
    }
  }
  rpc intri-config-Config-RunSaveRunningConfig {
  }
  rpc intri-config-Config-RunRestoreDefaultConfig {
    input {
      uses RestoreDefaultType;
    }
  }
}
