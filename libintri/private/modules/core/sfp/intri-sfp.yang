module intri-sfp {
  namespace "intri:intri-sfp";
  prefix "intri-sfp";
  import eventpb {
    prefix "eventpb";
  }
  organization "Intrising Inc.";
  contact "xxx@intrising.com.tw";
  revision 2022-06-14 {
    description "Build date.";
  }
}
