module intri-isolation {

  namespace "intri:intri-isolation";
  prefix "intri-isolation";
  organization "
    Intrising Inc.";
  contact "
    intrising@intrising.com.tw";
  revision 2022-06-24 {
    description "Build date.";
  }

  import intri-device {
    prefix intri-device;
  }
  import intri-empty {
    prefix intri-empty;
  }
  grouping ConfigEntry {
    container IdentifyNo {
      uses intri-device:InterfaceIdentify;
    }
    container AllowOutgoingList {
      list AllowOutgoingList_Entry {
        uses intri-device:InterfaceIdentify;
      }
    }
  }
  grouping Config {
    container List {
      list List_Entry {
        uses ConfigEntry;
      }
    }
  }
  rpc intri-isolation-Isolation-GetConfig {
    output {
      uses Config;
    }
  }
  rpc intri-isolation-Isolation-SetAllowOutgoingConfig {
    input {
      uses ConfigEntry;
    }
  }
}
