// Code generated by protoc-gen-yang. DO NOT EDIT.


/* ****************************************************************************************************
 * Import Path : "github.com/Intrising/intri-type/log"                                                *
 * Dir Path    : github.com/Intrising/intri-type/log                                                  *
 * Go Package  : log                                                                                  *
 * Files       : 3                                                                                    *
 **************************************************************************************************** */
module intri-log {

  namespace "intri:intri-log";

  prefix "intri-log";

  organization "Intrising Inc.";

  contact "intrising@intrising.com.tw";

  revision 2022-06-23 {
    description "Build date.";
  }

  import intri-event {
    prefix intri-event;
  }
  import intri-timestamp {
    prefix intri-timestamp;
  }
  import intri-empty {
    prefix intri-empty;
  }
  import intri-common {
    prefix intri-common;
  }


  /* **************************************************************************************************
   * Enums       : 1                                                                                  *
   ************************************************************************************************** */
  /* log/common.proto */
  typedef StorageTypeOptions {
    type enumeration {
      enum STORAGE_TYPE_FLASH {
        description "[Flash] Log file is stored in flash";
        value 0;
      }
      enum STORAGE_TYPE_RAM_DISK {
        description "[Ram Disk] Log file is stored in ram disk";
        value 1;
      }
    }
  }


  /* **************************************************************************************************
   * Msgs        : 9                                                                                  *
   ************************************************************************************************** */
  /* log/log.proto */
  grouping Config {
    container BasicConfig {
      uses BasicConfig;
    }
    container TargetConfig {
      uses TargetConfig;
    }
    container ActionConfig {
      uses ActionConfig;
    }
  }
  /* log/log.proto */
  grouping BasicConfig {
    leaf StorageOption {
      type StorageTypeOptions;
    }
  }
  /* log/log.proto */
  grouping TargetConfig {
    container List {
      list List_Entry {
        uses TargetConfigEntry;
      }
    }
  }
  /* log/log.proto */
  grouping TargetConfigEntry {
    leaf Name {
      type string;
    }
    leaf HostAddress {
      type string;
    }
    leaf TargetLogType {
      type intri-event:TargetLogTypeOptions;
    }
    leaf LoggingSeverityType {
      type intri-event:LoggingSeverityTypeOptions;
    }
    leaf LogConfigChanges {
      type boolean;
    }
    leaf LogDebugEventOnly {
      type boolean;
    }
    leaf SnmpV3Username {
      type string;
    }
    leaf SnmpTrapCommunity {
      type string;
    }
  }
  /* log/log.proto */
  grouping ActionConfig {
    container List {
      list List_Entry {
        uses ActionConfigEntry;
      }
    }
  }
  /* log/log.proto */
  grouping ActionConfigEntry {
    leaf LoggingType {
      type intri-event:LoggingTypeOptions;
    }
    leaf LoggingSeverityType {
      type intri-event:LoggingSeverityTypeOptions;
    }
  }
  /* log/log.proto */
  grouping Statistics {
    leaf NumberOfTargets {
      type uint64;
    }
    leaf SyslogCounter {
      type int32;
    }
    leaf SnmpTrapCounter {
      type int32;
    }
    leaf SnmpInfoCounter {
      type int32;
    }
    leaf DisplayInCliCounter {
      type int32;
    }
  }
  /* log/log.proto */
  grouping LogFileEntry {
    leaf LogID {
      type uint64;
    }
    container Ts {
      uses intri-timestamp:Timestamp;
    }
    leaf LoggingType {
      type intri-event:LoggingTypeOptions;
    }
    leaf LoggingSeverityType {
      type intri-event:LoggingSeverityTypeOptions;
    }
    leaf Message {
      type string;
    }
  }
  /* log/log.proto */
  grouping LogFiles {
    container List {
      list List_Entry {
        uses LogFileEntry;
      }
    }
  }


  /* **************************************************************************************************
   * Services    : 1                                                                                  *
   ************************************************************************************************** */

  /* **************************************************************************************************
   * Service     : Log                                                                                *
   * Methods     : 15                                                                                 *
   ************************************************************************************************** */
  /* log/service.proto */
  rpc intri-log-GetConfig {
    output  {
      uses Config;
    }
  }
  /* log/service.proto */
  rpc intri-log-GetBasicConfig {
    output  {
      uses BasicConfig;
    }
  }
  /* log/service.proto */
  rpc intri-log-UpdateBasicConfig {
    input  {
      uses BasicConfig;
    }
  }
  /* log/service.proto */
  rpc intri-log-GetTargetConfig {
    output  {
      uses TargetConfig;
    }
  }
  /* log/service.proto */
  rpc intri-log-AddTargetConfigEntry {
    input  {
      uses TargetConfigEntry;
    }
  }
  /* log/service.proto */
  rpc intri-log-UpdateTargetConfigEntry {
    input  {
      uses TargetConfigEntry;
    }
  }
  /* log/service.proto */
  rpc intri-log-DeleteTargetConfigEntry {
    input  {
      uses TargetConfigEntry;
    }
  }
  /* log/service.proto */
  rpc intri-log-GetActionConfig {
    output  {
      uses ActionConfig;
    }
  }
  /* log/service.proto */
  rpc intri-log-UpdateActionConfig {
    input  {
      uses ActionConfig;
    }
  }
  /* log/service.proto */
  rpc intri-log-RunSendTestEvent {
  }
  /* log/service.proto */
  rpc intri-log-GetStatistics {
    output  {
      uses Statistics;
    }
  }
  /* log/service.proto */
  rpc intri-log-RunCleanStatistics {
  }
  /* log/service.proto */
  rpc intri-log-GetRecordTargetLogList {
    output  {
      uses LogFiles;
    }
  }
  /* log/service.proto */
  rpc intri-log-RunCleanRecordTargetLogList {
  }
  /* log/service.proto */
  rpc intri-log-RunSaveLogToYAML {
    input  {
      uses intri-common:Path;
    }
  }

}
