module intri-ptp {
  namespace "intri:intri-ptp";
  prefix "intri-ptp";
  import ptppb {
    prefix "ptppb";
  }
  import protobufpb {
    prefix "protobufpb";
  }
  organization "Intrising Inc.";
  contact "xxx@intrising.com.tw";
  revision 2022-06-14 {
    description "Build date.";
  }
}
