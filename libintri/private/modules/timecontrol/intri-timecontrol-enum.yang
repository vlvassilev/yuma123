submodule intri-timecontrol-enum {
  belongs-to "intri-timecontrol" {
    prefix "intri-timecontrol-enum";
  }
  revision 2022-06-14 {
    description "Build date.";
  }
  // timecontrol/common.proto
  typedef StatusInputBitTypeOptions {
    type enumeration {
      enum STATUS_INPUT_BIT_TYPE_LOS_LIVE {
        description "[Los Live] Status input bit type los live";
        value 0;
      }
      enum STATUS_INPUT_BIT_TYPE_NO_ACTIVITY_LIVE {
        description "[No Activity Live] Status input bit type no activity live";
        value 1;
      }
      enum STATUS_INPUT_BIT_TYPE_REQ_OFFS_LIM_LIVE {
        description "[Req Offs Lim Live] Status input bit type req offs lim live";
        value 2;
      }
      enum STATUS_INPUT_BIT_TYPE_TRANS_DETECT_LIVE {
        description "[Trans Detect Live] Status input bit type trans detect live";
        value 3;
      }
    }
  }
  // timecontrol/common.proto
  typedef DPLLManageIndexTypeOptions {
    type enumeration {
      enum DPLL_MANAGE_INDEX_0 {
        description "[Index 0] Manage index 0";
        value 0;
      }
      enum DPLL_MANAGE_INDEX_1 {
        description "[Index 1] Manage index 1";
        value 1;
      }
      enum DPLL_MANAGE_INDEX_2 {
        description "[Index 2] Manage index 2";
        value 2;
      }
      enum DPLL_MANAGE_INDEX_3 {
        description "[Index 3] Manage index 3";
        value 3;
      }
      enum DPLL_MANAGE_INDEX_4 {
        description "[Index 4] Manage index 4";
        value 4;
      }
      enum DPLL_MANAGE_INDEX_5 {
        description "[Index 5] Manage index 5";
        value 5;
      }
      enum DPLL_MANAGE_INDEX_6 {
        description "[Index 6] Manage index 6";
        value 6;
      }
      enum DPLL_MANAGE_INDEX_7 {
        description "[Index 7] Manage index 7";
        value 7;
      }
    }
  }
  // timecontrol/common.proto
  typedef DPLLStatusBitTypeOptions {
    type enumeration {
      enum DPLL_STATUS_BIT_TYPE_FREERUN {
        description "[Freerun] Freerun";
        value 0;
      }
      enum DPLL_STATUS_BIT_TYPE_LOCKACQ {
        description "[Lockacq] Lockacq";
        value 1;
      }
      enum DPLL_STATUS_BIT_TYPE_LOCKREC {
        description "[Lockrec] Lockrec";
        value 2;
      }
      enum DPLL_STATUS_BIT_TYPE_LOCKED {
        description "[Locked] Locked";
        value 3;
      }
      enum DPLL_STATUS_BIT_TYPE_HOLDOVER {
        description "[Holdover] Holdover";
        value 4;
      }
      enum DPLL_STATUS_BIT_TYPE_OPENLOOP {
        description "[Openloop] Openloop";
        value 5;
      }
      enum DPLL_STATUS_BIT_TYPE_DISABLED {
        description "[Disabled] Disabled";
        value 6;
      }
    }
  }
  // timecontrol/common.proto
  typedef DPLLRefPriorityBitTypeOptions {
    type enumeration {
      enum DPLL_REF_PRIORITY_BIT_TYPE_0 {
        description "[Priority 0] Dpll ref priority bit type 0";
        value 0;
      }
      enum DPLL_REF_PRIORITY_BIT_TYPE_1 {
        description "[Priority 1] Dpll ref priority bit type 1";
        value 1;
      }
      enum DPLL_REF_PRIORITY_BIT_TYPE_2 {
        description "[Priority 2] Dpll ref priority bit type 2";
        value 2;
      }
      enum DPLL_REF_PRIORITY_BIT_TYPE_3 {
        description "[Priority 3] Dpll ref priority bit type 3";
        value 3;
      }
      enum DPLL_REF_PRIORITY_BIT_TYPE_4 {
        description "[Priority 4] Dpll ref priority bit type 4";
        value 4;
      }
      enum DPLL_REF_PRIORITY_BIT_TYPE_5 {
        description "[Priority 5] Dpll ref priority bit type 5";
        value 5;
      }
      enum DPLL_REF_PRIORITY_BIT_TYPE_6 {
        description "[Priority 6] Dpll ref priority bit type 6";
        value 6;
      }
      enum DPLL_REF_PRIORITY_BIT_TYPE_7 {
        description "[Priority 7] Dpll ref priority bit type 7";
        value 7;
      }
      enum DPLL_REF_PRIORITY_BIT_TYPE_8 {
        description "[Priority 8] Dpll ref priority bit type 8";
        value 8;
      }
      enum DPLL_REF_PRIORITY_BIT_TYPE_9 {
        description "[Priority 9] Dpll ref priority bit type 9";
        value 9;
      }
      enum DPLL_REF_PRIORITY_BIT_TYPE_10 {
        description "[Priority 10] Dpll ref priority bit type 10";
        value 10;
      }
      enum DPLL_REF_PRIORITY_BIT_TYPE_11 {
        description "[Priority 11] Dpll ref priority bit type 11";
        value 11;
      }
      enum DPLL_REF_PRIORITY_BIT_TYPE_12 {
        description "[Priority 12] Dpll ref priority bit type 12";
        value 12;
      }
      enum DPLL_REF_PRIORITY_BIT_TYPE_13 {
        description "[Priority 13] Dpll ref priority bit type 13";
        value 13;
      }
      enum DPLL_REF_PRIORITY_BIT_TYPE_14 {
        description "[Priority 14] Dpll ref priority bit type 14";
        value 14;
      }
      enum DPLL_REF_PRIORITY_BIT_TYPE_15 {
        description "[Priority 15] Dpll ref priority bit type 15";
        value 15;
      }
      enum DPLL_REF_PRIORITY_BIT_TYPE_16 {
        description "[Priority 16] Dpll ref priority bit type 16";
        value 16;
      }
      enum DPLL_REF_PRIORITY_BIT_TYPE_17 {
        description "[Priority 17] Dpll ref priority bit type 17";
        value 17;
      }
      enum DPLL_REF_PRIORITY_BIT_TYPE_18 {
        description "[Priority 18] Dpll ref priority bit type 18";
        value 18;
      }
    }
  }
  // timecontrol/common.proto
  typedef ToDSourceTypeOptions {
    type enumeration {
      enum SYSTEM {
        description "[SYSTEM] Source system";
        value 0;
      }
      enum TIME_CONTROL {
        description "[TIME_CONTROL] Source time_control";
        value 1;
      }
      enum RTC {
        description "[RTC] Source rtc";
        value 2;
      }
      enum GPS {
        description "[GPS] Source gps";
        value 3;
      }
    }
  }
  // timecontrol/common.proto
  typedef DPLLToDTypeOptions {
    type enumeration {
      enum DPLL_MANAGE_TOD_0 {
        description "[ToD 0] ToD 0";
        value 0;
      }
      enum DPLL_MANAGE_TOD_1 {
        description "[ToD 1] ToD 1";
        value 1;
      }
      enum DPLL_MANAGE_TOD_2 {
        description "[ToD 2] ToD 2";
        value 2;
      }
      enum DPLL_MANAGE_TOD_3 {
        description "[ToD 3] ToD 3";
        value 3;
      }
    }
  }
}
