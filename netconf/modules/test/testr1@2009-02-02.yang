module testr1 {

    namespace "http://netconfcentral.com/ns/testr1";
    prefix "r1";

    import testr2 {
        prefix r2;
        revision-date 2009-01-01;
    }

    organization
        "Netconf Central";

    contact
        "Andy Bierman";

    description
        "YANG import-by-revision test module.";

    revision 2009-02-02 {
        description "Initial version.";
    }
  
    grouping TestGroup1 {
       leaf X { type string; }
       leaf Y { type leafref { path "../X"; } }
       uses r2:TestGroup {
         augment E {
           when "../Y = 'fred'";
           container Z {
             presence "exists";
           }
         }
      }
    }

    container foo-r2 {
       uses r2:TestGroup;
    }

    container goo-local {
       uses r1:TestGroup1;
    }

    
}
