// Code generated by protoc-gen-yang. DO NOT EDIT.


/* ****************************************************************************************************
 * Import Path : "github.com/Intrising/intri-type/core/portsecurity"                                  *
 * Dir Path    : github.com/Intrising/intri-type/core/portsecurity                                    *
 * Go Package  : portsecurity                                                                         *
 * Files       : 3                                                                                    *
 **************************************************************************************************** */
module intri-portsecurity {

  namespace "intri:intri-portsecurity";

  prefix "intri-portsecurity";

  organization "Intrising Inc.";

  contact "intrising@intrising.com.tw";

  revision 2022-06-23 {
    description "Build date.";
  }

  import intri-device {
    prefix intri-device;
  }
  import intri-empty {
    prefix intri-empty;
  }


  /* **************************************************************************************************
   * Enums       : 4                                                                                  *
   ************************************************************************************************** */
  /* core/portsecurity/common.proto */
  typedef PortSecurityModeTypeOptions {
    type enumeration {
      enum PORT_SECURITY_MODE_TYPE_STATIC {
        description "[Static]";
        value 0;
      }
      enum PORT_SECURITY_MODE_TYPE_STICKY {
        description "[Sticky]";
        value 1;
      }
      enum PORT_SECURITY_MODE_TYPE_DYNAMIC {
        description "[Dynamic]";
        value 2;
      }
    }
  }
  /* core/portsecurity/common.proto */
  typedef PortSecurityAgeModeTypeOptions {
    type enumeration {
      enum PORT_SECURITY_AGE_MODE_TYPE_ABSOULTE {
        description "[Absolute] Absolute aging";
        value 0;
      }
      enum PORT_SECURITY_AGE_MODE_TYPE_INACTIVITY {
        description "[Inactivity] Aging based on inactivity time period";
        value 1;
      }
    }
  }
  /* core/portsecurity/common.proto */
  typedef PortSecurityViolationTypeOptions {
    type enumeration {
      enum PORT_SECURITY_VIOLATION_TYPE_SHUTDOWN {
        description "[Shutdown] Security violation shutdown mode";
        value 0;
      }
      enum PORT_SECURITY_VIOLATION_TYPE_DISCARD {
        description "[Discard] Security violation discard mode";
        value 1;
      }
      enum PORT_SECURITY_VIOLATION_TYPE_RESTRICT {
        description "[Restrict] Security violation restrict mode";
        value 2;
      }
    }
  }
  /* core/portsecurity/common.proto */
  typedef PortSecurityStatusTypeOptions {
    type enumeration {
      enum PORT_SECURITY_STATUS_TYPE_SECURE_DOWN {
        description "[Secure-Down]";
        value 0;
      }
      enum PORT_SECURITY_STATUS_TYPE_SECURE_UP {
        description "[Secure-Up]";
        value 1;
      }
      enum PORT_SECURITY_STATUS_TYPE_SECURE_SHUTDOWN {
        description "[Secure-Shutdown]";
        value 2;
      }
    }
  }


  /* **************************************************************************************************
   * Msgs        : 7                                                                                  *
   ************************************************************************************************** */
  /* core/portsecurity/portsecurity.proto */
  grouping Config {
    container List {
      list List_Entry {
        uses PortSecurityConfigEntry;
      }
    }
  }
  /* core/portsecurity/portsecurity.proto */
  grouping PortSecurityConfigEntry {
    container IdentifyNo {
      uses intri-device:InterfaceIdentify;
    }
    leaf Enabled {
      type boolean;
    }
    leaf Mode {
      type PortSecurityModeTypeOptions;
    }
    leaf MaxMACCount {
      type int32;
    }
    container SecureAddressList {
      list SecureAddressList_Entry {
        uses SecureEntry;
      }
    }
    leaf ViolationMode {
      type PortSecurityViolationTypeOptions;
    }
  }
  /* core/portsecurity/portsecurity.proto */
  grouping SecureEntry {
    leaf VlanID {
      type int32;
    }
    leaf MACAddress {
      type string;
    }
  }
  /* core/portsecurity/portsecurity.proto */
  grouping PortSecureEntry {
    container IdentifyNo {
      uses intri-device:InterfaceIdentify;
    }
    container Entry {
      uses SecureEntry;
    }
  }
  /* core/portsecurity/portsecurity.proto */
  grouping Status {
    container List {
      list List_Entry {
        uses PortSecurityStatusEntry;
      }
    }
  }
  /* core/portsecurity/portsecurity.proto */
  grouping PortSecurityStatusEntry {
    container IdentifyNo {
      uses intri-device:InterfaceIdentify;
    }
    leaf Enabled {
      type boolean;
    }
    leaf Status {
      type PortSecurityStatusTypeOptions;
    }
    leaf ViolationMode {
      type PortSecurityViolationTypeOptions;
    }
    leaf MaxMACCount {
      type int32;
    }
    leaf SecureMACCount {
      type int32;
    }
    leaf LastSourceMACaddressVlan {
      type string;
    }
  }
  /* core/portsecurity/portsecurity.proto */
  grouping PortSecurityAge {
    leaf StaticAging {
      type boolean;
    }
    leaf Type {
      type PortSecurityAgeModeTypeOptions;
    }
    leaf Time {
      type int32;
    }
  }


  /* **************************************************************************************************
   * Services    : 1                                                                                  *
   ************************************************************************************************** */

  /* **************************************************************************************************
   * Service     : PortSecurity                                                                       *
   * Methods     : 5                                                                                  *
   ************************************************************************************************** */
  /* core/portsecurity/service.proto */
  rpc intri-portsecurity-GetConfig {
    output  {
      uses Config;
    }
  }
  /* core/portsecurity/service.proto */
  rpc intri-portsecurity-UpdatePortSecurityConfig {
    input  {
      uses PortSecurityConfigEntry;
    }
  }
  /* core/portsecurity/service.proto */
  rpc intri-portsecurity-AddPortSecureEntry {
    input  {
      uses PortSecureEntry;
    }
  }
  /* core/portsecurity/service.proto */
  rpc intri-portsecurity-DeletePortSecureEntry {
    input  {
      uses PortSecureEntry;
    }
  }
  /* core/portsecurity/service.proto */
  rpc intri-portsecurity-GetPortSecurityInfo {
    output  {
      uses Status;
    }
  }

}
