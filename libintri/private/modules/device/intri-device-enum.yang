submodule intri-device-enum {
  belongs-to "intri-device" {
    prefix "intri-device-enum";
  }
  revision 2022-06-14 {
    description "Build date.";
  }
  // device/board.proto
  typedef RCLKTypeOptions {
    type enumeration {
      enum RCLK_TYPE_0 {
        description "[RCLK 0] RCLK 0";
        value 0;
      }
      enum RCLK_TYPE_1 {
        description "[RCLK 1] RCLK 1";
        value 1;
      }
    }
  }
  // device/board.proto
  typedef InputClockIndexTypeOptions {
    type enumeration {
      enum INPUT_CLOCK_INDEX_TYPE_0 {
        description "[Clock Index 0] Clock Index 0";
        value 0;
      }
      enum INPUT_CLOCK_INDEX_TYPE_1 {
        description "[Clock Index 1] Clock Index 1";
        value 1;
      }
      enum INPUT_CLOCK_INDEX_TYPE_2 {
        description "[Clock Index 2] Clock Index 2";
        value 2;
      }
      enum INPUT_CLOCK_INDEX_TYPE_3 {
        description "[Clock Index 3] Clock Index 3";
        value 3;
      }
      enum INPUT_CLOCK_INDEX_TYPE_4 {
        description "[Clock Index 4] Clock Index 4";
        value 4;
      }
      enum INPUT_CLOCK_INDEX_TYPE_5 {
        description "[Clock Index 5] Clock Index 5";
        value 5;
      }
      enum INPUT_CLOCK_INDEX_TYPE_6 {
        description "[Clock Index 6] Clock Index 6";
        value 6;
      }
      enum INPUT_CLOCK_INDEX_TYPE_7 {
        description "[Clock Index 7] Clock Index 7";
        value 7;
      }
      enum INPUT_CLOCK_INDEX_TYPE_8 {
        description "[Clock Index 8] Clock Index 8";
        value 8;
      }
      enum INPUT_CLOCK_INDEX_TYPE_9 {
        description "[Clock Index 9] Clock Index 9";
        value 9;
      }
      enum INPUT_CLOCK_INDEX_TYPE_10 {
        description "[Clock Index 10] Clock Index 10";
        value 10;
      }
      enum INPUT_CLOCK_INDEX_TYPE_11 {
        description "[Clock Index 11] Clock Index 11";
        value 11;
      }
      enum INPUT_CLOCK_INDEX_TYPE_12 {
        description "[Clock Index 12] Clock Index 12";
        value 12;
      }
      enum INPUT_CLOCK_INDEX_TYPE_13 {
        description "[Clock Index 13] Clock Index 13";
        value 13;
      }
      enum INPUT_CLOCK_INDEX_TYPE_14 {
        description "[Clock Index 14] Clock Index 14";
        value 14;
      }
      enum INPUT_CLOCK_INDEX_TYPE_15 {
        description "[Clock Index 15] Clock Index 15";
        value 15;
      }
    }
  }
  // device/board.proto
  typedef InputClockTypeOptions {
    type enumeration {
      enum INPUT_CLOCK_TYPE_MAC_CLOCK_0 {
        description "[MAC Clock 0] MAC Clock 0";
        value 0;
      }
      enum INPUT_CLOCK_TYPE_MAC_CLOCK_1 {
        description "[MAC Clock 1] MAC Clock 1";
        value 1;
      }
      enum INPUT_CLOCK_TYPE_PHY_A_CLOCK_0 {
        description "[PHY A Clock 0] PHY A Clock 0";
        value 2;
      }
      enum INPUT_CLOCK_TYPE_PHY_A_CLOCK_1 {
        description "[PHY A Clock 1] PHY A Clock 1";
        value 3;
      }
      enum INPUT_CLOCK_TYPE_PHY_B_CLOCK_0 {
        description "[PHY B Clock 0] PHY B Clock 0";
        value 4;
      }
      enum INPUT_CLOCK_TYPE_PHY_B_CLOCK_1 {
        description "[PHY B Clock 1] PHY B Clock 1";
        value 5;
      }
      enum INPUT_CLOCK_TYPE_PHY_C_CLOCK_0 {
        description "[PHY C Clock 0] PHY C Clock 0";
        value 6;
      }
      enum INPUT_CLOCK_TYPE_PHY_C_CLOCK_1 {
        description "[PHY C Clock 1] PHY C Clock 1";
        value 7;
      }
      enum INPUT_CLOCK_TYPE_BITS_IN {
        description "[Bits In] Bits In";
        value 8;
      }
      enum INPUT_CLOCK_TYPE_1PPS_GPS {
        description "[1pps GPS] 1pps GPS";
        value 10;
      }
      enum INPUT_CLOCK_TYPE_1PPS_IN {
        description "[1pps In] 1pps In";
        value 11;
      }
      enum INPUT_CLOCK_TYPE_10MHZ_IN {
        description "[10Mhz In] 10Mhz In";
        value 12;
      }
      enum INPUT_CLOCK_TYPE_1PPS_FEEDBACK {
        description "[1pps Feedback] 1pps Feedback";
        value 13;
      }
    }
  }
  // device/board.proto
  typedef LedTypeOptions {
    type enumeration {
      enum LED_TYPE_OFF {
        description "[Off]";
        value 0;
      }
      enum LED_TYPE_ON {
        description "[On]";
        value 1;
      }
      enum LED_TYPE_ORANGE {
        description "[Orange]";
        value 2;
      }
      enum LED_TYPE_GREEN {
        description "[Green]";
        value 3;
      }
    }
  }
  // device/board.proto
  typedef PhyInterfaceTypeOptions {
    type enumeration {
      enum PHY_INTERFACE_TYPE_SMI {
        description "[Smi]";
        value 0;
      }
      enum PHY_INTERFACE_TYPE_XSMI {
        description "[Xsmi]";
        value 1;
      }
      enum PHY_INTERFACE_TYPE_UNUSED {
        description "[Unused]";
        value 2;
      }
    }
  }
  // device/board.proto
  typedef FactoryHwFeatureTypeOptions {
    type enumeration {
      enum FACTORY_HW_FEATURE_TYPE_POE_PLUS_PLUS {
        description "[PoE++] Power over Ethernet plus (30W ports) supported";
        value 0;
      }
      enum FACTORY_HW_FEATURE_TYPE_POE_PLUS {
        description "[PoE+] Power over Ethernet plus (30W ports) supported";
        value 1;
      }
      enum FACTORY_HW_FEATURE_TYPE_EEE {
        description "[EEE] Energy Efficient Ethernet";
        value 2;
      }
      enum FACTORY_HW_FEATURE_TYPE_RTC {
        description "[RTC] Local real time clock";
        value 3;
      }
      enum FACTORY_HW_FEATURE_TYPE_SFP {
        description "[SFP] Pluggable optical port";
        value 4;
      }
    }
  }
  // device/board.proto
  typedef PortPropertyTypeOptions {
    type enumeration {
      enum PORT_PROPERTIES_TYPE_10M_FULL {
        description "[10M FULL] This port is capable of running at 10Mbit/s";
        value 0;
      }
      enum PORT_PROPERTIES_TYPE_10M_HALF {
        description "[10M HALF] This port is capable of running at 10Mbit/s";
        value 1;
      }
      enum PORT_PROPERTIES_TYPE_100M_FULL {
        description "[100M FULL] This port is capable of running at 100Mbit/s";
        value 2;
      }
      enum PORT_PROPERTIES_TYPE_100M_HALF {
        description "[100M HALF] This port is capable of running at 100Mbit/s";
        value 3;
      }
      enum PORT_PROPERTIES_TYPE_1000M_FULL {
        description "[1G FULL] This port is capable of running at 1000Mbit/s";
        value 4;
      }
      enum PORT_PROPERTIES_TYPE_2500M_FULL {
        description "[2.5G FULL] This port is capable of running at 2500Mbit/s";
        value 5;
      }
      enum PORT_PROPERTIES_TYPE_5G_FULL {
        description "[5G FULL] This port is capable of running at 5Gbit/s";
        value 6;
      }
      enum PORT_PROPERTIES_TYPE_10G_FULL {
        description "[10G FULL] This port is capable of running at 10Gbit/s";
        value 7;
      }
      enum PORT_PROPERTIES_TYPE_25G_FULL {
        description "[25G FULL] This port is capable of running at 25Gbit/s";
        value 8;
      }
      enum PORT_PROPERTIES_TYPE_RJ45 {
        description "[RJ45] This port uses as RJ45 connector";
        value 9;
      }
      enum PORT_PROPERTIES_TYPE_SFP {
        description "[SFP] This port uses a pluggable SFP";
        value 10;
      }
      enum PORT_PROPERTIES_TYPE_POE {
        description "[PoE] This port is capable to supply Power over Ethernet (PoE)";
        value 11;
      }
      enum PORT_PROPERTIES_TYPE_POE_PLUS {
        description "[PoE+] This port is capable to supply Power over Ethernet Extended (PoE+)";
        value 12;
      }
      enum PORT_PROPERTIES_TYPE_POE_PLUS_PLUS {
        description "[PoE++] This port is capable to supply Power over Ethernet Extended (PoE+)";
        value 13;
      }
      enum PORT_PROPERTIES_TYPE_LINK_PORT {
        description "[Link Port] This port is capable to supply Power over Ethernet Extended (PoE+)";
        value 14;
      }
    }
  }
  // device/board.proto
  typedef DevicePortSpeedDuplexTypeOptions {
    type enumeration {
      enum DEVICE_PORT_SPEED_DUPLEX_TYPE_AUTO {
        description "[Auto]";
        value 0;
      }
      enum DEVICE_PORT_SPEED_DUPLEX_TYPE_10M_FULL {
        description "[10 Mbps / Full]";
        value 1;
      }
      enum DEVICE_PORT_SPEED_DUPLEX_TYPE_10M_HALF {
        description "[10 Mbps / Half]";
        value 2;
      }
      enum DEVICE_PORT_SPEED_DUPLEX_TYPE_100M_FULL {
        description "[100 Mbps / Full]";
        value 3;
      }
      enum DEVICE_PORT_SPEED_DUPLEX_TYPE_100M_HALF {
        description "[100 Mbps / Half]";
        value 4;
      }
      enum DEVICE_PORT_SPEED_DUPLEX_TYPE_1000M_FULL {
        description "[1 Gbps  / Full]";
        value 5;
      }
      enum DEVICE_PORT_SPEED_DUPLEX_TYPE_2500M_FULL {
        description "[2.5 Gbps / Full]";
        value 6;
      }
      enum DEVICE_PORT_SPEED_DUPLEX_TYPE_5G_FULL {
        description "[5 Gbps / Full]";
        value 7;
      }
      enum DEVICE_PORT_SPEED_DUPLEX_TYPE_10G_FULL {
        description "[10 Gbps / Full]";
        value 8;
      }
      enum DEVICE_PORT_SPEED_DUPLEX_TYPE_25G_FULL {
        description "[25 Gbps / Full]";
        value 9;
      }
      enum DEVICE_PORT_SPEED_DUPLEX_TYPE_40G_FULL {
        description "[40 Gbps / Full]";
        value 10;
      }
      enum DEVICE_PORT_SPEED_DUPLEX_TYPE_100G_FULL {
        description "[100 Gbps / Full]";
        value 11;
      }
      enum DEVICE_PORT_SPEED_DUPLEX_TYPE_NA {
        description "[NA]";
        value 12;
      }
    }
  }
  // device/board.proto
  typedef PortInterfaceTypeOptions {
    type enumeration {
      enum PORT_INTERFACE_TYPE_COPPER {
        description "[Copper] Normal copper interface";
        value 0;
      }
      enum PORT_INTERFACE_TYPE_OPTICAL {
        description "[Optical] Optical interface";
        value 1;
      }
    }
  }
  // device/board.proto
  typedef DeviceTypeOptions {
    type enumeration {
      enum DEVICE_TYPE_MCU {
        description "[MCU] MCU";
        value 0;
      }
      enum DEVICE_TYPE_I2C {
        description "[I2C] I2C";
        value 1;
      }
      enum DEVICE_TYPE_GPIO {
        description "[GPIO] GPIO";
        value 2;
      }
    }
  }
  // device/board.proto
  typedef MonitorTypeOptions {
    type enumeration {
      enum MONITOR_TYPE_TEMP_OK {
        description "[Temperature Normal] Temperature Normal";
        value 0;
      }
      enum MONITOR_TYPE_TEMP_WARN {
        description "[Temperature Warning] Temperature Warning";
        value 1;
      }
      enum MONITOR_TYPE_FAN_OK {
        description "[Fan Speed Ok] Fan Speed Ok";
        value 2;
      }
      enum MONITOR_TYPE_FAN_WARN {
        description "[Fan Speed Warn] Fan Speed Warn";
        value 3;
      }
    }
  }
  // device/board.proto
  typedef PSUTypeOptions {
    type enumeration {
      enum PSU_TYPE_LOCATION_OK {
        description "[Location Ok] Location Ok";
        value 0;
      }
      enum PSU_TYPE_LOCATION_WARN {
        description "[Location Warn] Location Warn";
        value 1;
      }
      enum PSU_TYPE_AC_OK {
        description "[AC Ok] AC Ok";
        value 2;
      }
      enum PSU_TYPE_AC_WARN {
        description "[AC Warning] AC Warning";
        value 3;
      }
      enum PSU_TYPE_PW_OK {
        description "[Power Ok] Power Ok";
        value 4;
      }
      enum PSU_TYPE_PW_WARN {
        description "[Power Warning] Power Warning";
        value 5;
      }
      enum PSU_TYPE_FAIL {
        description "[PSU Failed] Failed";
        value 6;
      }
    }
  }
  // device/board.proto
  typedef FanTypeOptions {
    type enumeration {
      enum FAN_TYPE_RPM {
        description "[RPM] RPM";
        value 0;
      }
    }
  }
  // device/board.proto
  typedef FanDeviceTypeOptions {
    type enumeration {
      enum FAN_DEVICE_TYPE_RPM {
        description "[RPM] RPM";
        value 0;
      }
    }
  }
  // device/board.proto
  typedef PoEDeviceTypeOptions {
    type enumeration {
      enum POE_DEVICE_TYPE_I2C {
        description "[I2C] I2C";
        value 0;
      }
      enum POE_DEVICE_TYPE_UART {
        description "[UART] UART";
        value 1;
      }
    }
  }
  // device/boundary.proto
  typedef BoundaryTypeOptions {
    type enumeration {
      enum BOUNDARY_TYPE_INT {
        description "[Int]";
        value 0;
      }
      enum BOUNDARY_TYPE_DOUBLE {
        description "[Double]";
        value 1;
      }
    }
  }
  // device/device.proto
  typedef LayerTypeOptions {
    type enumeration {
      enum LAYER_TYPE_L2 {
        description "[L2]";
        value 0;
      }
      enum LAYER_TYPE_L3 {
        description "[L3]";
        value 1;
      }
    }
  }
  // device/device.proto
  typedef InterfaceTypeOptions {
    type enumeration {
      enum INTERFACE_TYPE_VLAN {
        description "[VLAN]";
        value 0;
      }
      enum INTERFACE_TYPE_PORT {
        description "[Port]";
        value 1;
      }
      enum INTERFACE_TYPE_TRUNK {
        description "[LAG]";
        value 2;
      }
      enum INTERFACE_TYPE_MULTICAST {
        description "[Multicast]";
        value 3;
      }
    }
  }
}
