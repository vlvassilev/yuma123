submodule intri-access-enum {
  belongs-to "intri-access" {
    prefix "intri-access-enum";
  }
  revision 2022-06-14 {
    description "Build date.";
  }
  // core/access/authentication.proto
  typedef AuthenticationModeTypeOptions {
    type enumeration {
      enum AUTHENTICATION_MODE_TYPE_LOCAL {
        description "[Local] Verify against local database";
        value 0;
      }
      enum AUTHENTICATION_MODE_TYPE_LOCAL_THEN_RADIUS {
        description "[Local Then RADIUS] Verify against local database then try RADIUS server if user is not locally defined";
        value 1;
      }
      enum AUTHENTICATION_MODE_TYPE_RADIUS {
        description "[RADIUS] Verify against RADIUS server";
        value 2;
      }
      enum AUTHENTICATION_MODE_TYPE_LOCAL_THEN_TACACS {
        description "[Local Then TACACS+] Verify against local database then try TACACS+ server if user is not locally defined";
        value 3;
      }
      enum AUTHENTICATION_MODE_TYPE_TACACS {
        description "[TACACS+] Verify against TACACS+ server";
        value 4;
      }
      enum AUTHENTICATION_MODE_TYPE_RADIUS_THEN_LOCAL {
        description "[RADIUS Then Local] Verify against RADIUS server then try local database";
        value 5;
      }
      enum AUTHENTICATION_MODE_TYPE_TACACS_THEN_LOCAL {
        description "[TACACS+ Then Local] Verify against TACACS+ server then try local database";
        value 6;
      }
    }
  }
  // core/access/authserver.proto
  typedef AuthenticationServerTypeOptions {
    type enumeration {
      enum AUTHENTICATION_SERVER_TYPE_RADIUS {
        description "[RADIUS]";
        value 0;
      }
      enum AUTHENTICATION_SERVER_TYPE_TACACS {
        description "[TACACS+]";
        value 1;
      }
    }
  }
  // core/access/restriction.proto
  typedef RestrictionModeTypeOptions {
    type enumeration {
      enum RESTRICTION_MODE_TYPE_UNUSED {
        description "[Unused]";
        value 0;
      }
      enum RESTRICTION_MODE_TYPE_PERMIT {
        description "[Permit]";
        value 1;
      }
      enum RESTRICTION_MODE_TYPE_DENY {
        description "[Deny]";
        value 2;
      }
    }
  }
  // core/access/user.proto
  typedef RightsTypeOptions {
    type enumeration {
      enum RIGHTS_TYPE_NO_ACCESS {
        description "[No Access]";
        value 0;
      }
      enum RIGHTS_TYPE_EXECUTE_ONLY {
        description "[Execute Only]";
        value 1;
      }
      enum RIGHTS_TYPE_READ_ONLY {
        description "[Read Only]";
        value 2;
      }
      enum RIGHTS_TYPE_READ_WRITE {
        description "[Read Write]";
        value 3;
      }
      enum RIGHTS_TYPE_READ_EXECUTE {
        description "[Read Execute]";
        value 4;
      }
      enum RIGHTS_TYPE_READ_WRITE_EXECUTE {
        description "[Read Write Execute]";
        value 5;
      }
    }
  }
  // core/access/user.proto
  typedef UserEntrySNMPV3SecurityLevelTypeOptions {
    type enumeration {
      enum USER_ENTRY_SNMP_V3_SECURITY_LEVEL_TYPE_NO_AUTH_NO_PRIV {
        description "[None]";
        value 0;
      }
      enum USER_ENTRY_SNMP_V3_SECURITY_LEVEL_TYPE_AUTH_NO_PRIV {
        description "[Only Auth]";
        value 1;
      }
      enum USER_ENTRY_SNMP_V3_SECURITY_LEVEL_TYPE_AUTH_PRIV {
        description "[Auth & Privacy]";
        value 2;
      }
    }
  }
  // core/access/user.proto
  typedef UserEntrySNMPV3AuthAlgorithmTypeOptions {
    type enumeration {
      enum USER_ENTRY_SNMP_V3_AUTH_ALGORITHM_TYPE_NO_AUTHENTICATION {
        description "[None]";
        value 0;
      }
      enum USER_ENTRY_SNMP_V3_AUTH_ALGORITHM_TYPE_MD5 {
        description "[MD5]";
        value 1;
      }
      enum USER_ENTRY_SNMP_V3_AUTH_ALGORITHM_TYPE_SHA_1 {
        description "[SHA 1]";
        value 2;
      }
      enum USER_ENTRY_SNMP_V3_AUTH_ALGORITHM_TYPE_SHA_256 {
        description "[SHA 256]";
        value 3;
      }
    }
  }
  // core/access/user.proto
  typedef UserEntrySNMPV3PrivacyAlgorithmTypeOptions {
    type enumeration {
      enum USER_ENTRY_SNMP_V3_PRIVACY_ALGORITHM_TYPE_NO_PRIVACY {
        description "[None]";
        value 0;
      }
      enum USER_ENTRY_SNMP_V3_PRIVACY_ALGORITHM_TYPE_DES {
        description "[DES]";
        value 1;
      }
      enum USER_ENTRY_SNMP_V3_PRIVACY_ALGORITHM_TYPE_AES {
        description "[AES]";
        value 2;
      }
      enum USER_ENTRY_SNMP_V3_PRIVACY_ALGORITHM_TYPE_AES_192 {
        description "[AES 192]";
        value 3;
      }
      enum USER_ENTRY_SNMP_V3_PRIVACY_ALGORITHM_TYPE_AES_256 {
        description "[AES 256]";
        value 4;
      }
    }
  }
}
