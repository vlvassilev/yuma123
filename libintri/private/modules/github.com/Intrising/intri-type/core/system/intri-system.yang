// Code generated by protoc-gen-yang. DO NOT EDIT.


/* ****************************************************************************************************
 * Import Path : "github.com/Intrising/intri-type/core/system"                                        *
 * Dir Path    : github.com/Intrising/intri-type/core/system                                          *
 * Go Package  : system                                                                               *
 * Files       : 3                                                                                    *
 **************************************************************************************************** */
module intri-system {

  namespace "intri:intri-system";

  prefix "intri-system";

  organization "Intrising Inc.";

  contact "intrising@intrising.com.tw";

  revision 2022-06-23 {
    description "Build date.";
  }

  import intri-empty {
    prefix intri-empty;
  }


  /* **************************************************************************************************
   * Msgs        : 3                                                                                  *
   ************************************************************************************************** */
  /* core/system/system.proto */
  grouping Status {
    leaf LastBootTime {
      type string;
    }
    leaf Uptime {
      type int64;
    }
  }
  /* core/system/system.proto */
  grouping Config {
    leaf SysName {
      type string;
    }
    leaf SysLocation {
      type string;
    }
    leaf SysGroup {
      type string;
    }
    leaf SysContact {
      type string;
    }
  }
  /* core/system/identification.proto */
  grouping IdentificationConfig {
    leaf SysName {
      type string;
    }
    leaf SysLocation {
      type string;
    }
    leaf SysGroup {
      type string;
    }
    leaf SysContact {
      type string;
    }
  }


  /* **************************************************************************************************
   * Services    : 1                                                                                  *
   ************************************************************************************************** */

  /* **************************************************************************************************
   * Service     : System                                                                             *
   * Methods     : 3                                                                                  *
   ************************************************************************************************** */
  /* core/system/service.proto */
  rpc intri-system-GetConfig {
    output  {
      uses Config;
    }
  }
  /* core/system/service.proto */
  rpc intri-system-SetConfig {
    input  {
      uses Config;
    }
  }
  /* core/system/service.proto */
  rpc intri-system-GetStatus {
    output  {
      uses Status;
    }
  }

}
