module intri-test {

  namespace "http://intri.com.tw";

  prefix intri-test;

  organization 
    "Intrising Inc.";

  contact 
    "xxx <xxx@intrising.com.tw>";

  description 
    "test APIs";

  revision 2022-05-24 {
    description "Test progress.";
  }

  container test-apis {
    config false;

    description
      "/test-apis call the internal APIs to get information.";

    container test-counter {
      description
        "/test-apis/test-feat call the test API to get dynamic counter.";

      leaf counter {
        type uint64;
        description
          "Test for the counter of the calls get times";
      }
    }

    container test-mac-addr {
      description
        "/test-apis/test-addr call the test API to get device mac address.";

      leaf mac-addr {
        type string;
        description
          "Test get device mac address";
      }
    }
  }
}
