submodule intri-stp-enum {
  belongs-to "intri-stp" {
    prefix "intri-stp-enum";
  }
  revision 2022-06-14 {
    description "Build date.";
  }
  // core/stp/stp.proto
  typedef BridgeConfigModeTypeOptions {
    type enumeration {
      enum BRIDGE_CONFIG_MODE_TYPE_DISABLED {
        description "[Disabled] Disabled mode";
        value 0;
      }
      enum BRIDGE_CONFIG_MODE_TYPE_STP {
        description "[STP] Stp bridge mode";
        value 1;
      }
      enum BRIDGE_CONFIG_MODE_TYPE_RSTP {
        description "[RSTP] Rstp bridge mode";
        value 2;
      }
      enum BRIDGE_CONFIG_MODE_TYPE_MSTP {
        description "[MSTP] Mstp bridge mode";
        value 3;
      }
    }
  }
  // core/stp/stp.proto
  typedef PortConfigAdminP2PPortTypeOptions {
    type enumeration {
      enum PORT_CONFIG_ADMIN_P2P_PORT_TYPE_AUTO {
        description "[Auto] Auto mode";
        value 0;
      }
      enum PORT_CONFIG_ADMIN_P2P_PORT_TYPE_FORCE_FALSE {
        description "[Force False] Force false mode";
        value 1;
      }
      enum PORT_CONFIG_ADMIN_P2P_PORT_TYPE_FORCE_TRUE {
        description "[Force True] Force true mode";
        value 2;
      }
    }
  }
  // core/stp/stp.proto
  typedef PortConfigBPDUGuardTypeOptions {
    type enumeration {
      enum PORT_CONFIG_BPDU_GUARD_TYPE_DISABLED {
        description "[Disabled] Disabled mode";
        value 0;
      }
      enum PORT_CONFIG_BPDU_GUARD_TYPE_DROP_AND_EVENT {
        description "[Drop And Event] Drop and event mode";
        value 1;
      }
      enum PORT_CONFIG_BPDU_GUARD_TYPE_BLOCK_PORT {
        description "[Block Port] Block port mode";
        value 2;
      }
    }
  }
  // core/stp/stp.proto
  typedef PortStatusStateTypeOptions {
    type enumeration {
      enum PORT_STATUS_STATE_TYPE_UNKNOWN {
        description "[Unknown] Unknown state";
        value 0;
      }
      enum PORT_STATUS_STATE_TYPE_DISCARDING {
        description "[Discarding] Discarding state";
        value 1;
      }
      enum PORT_STATUS_STATE_TYPE_LEARNING {
        description "[Learning] Learning state ";
        value 2;
      }
      enum PORT_STATUS_STATE_TYPE_FORWARDING {
        description "[Forwarding] Forwarding state";
        value 3;
      }
      enum PORT_STATUS_STATE_TYPE_BLOCKING {
        description "[Blocking] Blocking state";
        value 4;
      }
      enum PORT_STATUS_STATE_TYPE_LISTENING {
        description "[Listening] Listening state";
        value 5;
      }
      enum PORT_STATUS_STATE_TYPE_BROKEN {
        description "[Broken] Broken state";
        value 6;
      }
    }
  }
  // core/stp/stp.proto
  typedef PortStatusRoleTypeOptions {
    type enumeration {
      enum PORT_STATUS_ROLE_TYPE_UNKNOWN {
        description "[Unknown] Unknown";
        value 0;
      }
      enum PORT_STATUS_ROLE_TYPE_ROOT {
        description "[Root bridge] Root bridge";
        value 1;
      }
      enum PORT_STATUS_ROLE_TYPE_DESIGNATED {
        description "[Designated bridge] Designated bridge";
        value 2;
      }
      enum PORT_STATUS_ROLE_TYPE_ALTERNATE {
        description "[Alternate bridge] Alternate bridge";
        value 3;
      }
      enum PORT_STATUS_ROLE_TYPE_BACKUP {
        description "[Backup bridge] Backup bridge";
        value 4;
      }
      enum PORT_STATUS_ROLE_TYPE_MASTER {
        description "[Master bridge] Master bridge";
        value 5;
      }
      enum PORT_STATUS_ROLE_TYPE_DISABLED {
        description "[Disabled] Disabled";
        value 6;
      }
    }
  }
}
