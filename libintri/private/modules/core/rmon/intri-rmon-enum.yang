submodule intri-rmon-enum {
  belongs-to "intri-rmon" {
    prefix "intri-rmon-enum";
  }
  revision 2022-06-14 {
    description "Build date.";
  }
  // core/rmon/rmon.proto
  typedef UtilizationIntervalTypeOptions {
    type enumeration {
      enum UTILIZATION_INTERVAL_TYPE_NOW {
        description "[Now]";
        value 0;
      }
      enum UTILIZATION_INTERVAL_TYPE_30_SECONDS {
        description "[30s]";
        value 1;
      }
      enum UTILIZATION_INTERVAL_TYPE_5_MINUTES {
        description "[5min]";
        value 2;
      }
    }
  }
}
