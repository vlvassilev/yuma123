module intri-diagnostic {
  namespace "intri:intri-diagnostic";
  prefix "intri-diagnostic";
  import diagnosticpb {
    prefix "diagnosticpb";
  }
  organization "Intrising Inc.";
  contact "xxx@intrising.com.tw";
  revision 2022-06-14 {
    description "Build date.";
  }
}
