// Code generated by protoc-gen-yang. DO NOT EDIT.


/* ****************************************************************************************************
 * Import Path : "github.com/Intrising/intri-type/snmptrap"                                           *
 * Dir Path    : github.com/Intrising/intri-type/snmptrap                                             *
 * Go Package  : snmptrap                                                                             *
 * Files       : 2                                                                                    *
 **************************************************************************************************** */
module intri-snmptrap {

  namespace "intri:intri-snmptrap";

  prefix "intri-snmptrap";

  organization "Intrising Inc.";

  contact "intrising@intrising.com.tw";

  revision 2022-06-23 {
    description "Build date.";
  }

  import intri-access {
    prefix intri-access;
  }
  import intri-empty {
    prefix intri-empty;
  }
  import intri-userinterface {
    prefix intri-userinterface;
  }


  /* **************************************************************************************************
   * Msgs        : 1                                                                                  *
   ************************************************************************************************** */
  /* snmptrap/snmptrap.proto */
  grouping SNMPTrapCounter {
    leaf ErrorCounts {
      type int32;
    }
    leaf TrapCounts {
      type int32;
    }
  }


  /* **************************************************************************************************
   * Services    : 1                                                                                  *
   ************************************************************************************************** */

  /* **************************************************************************************************
   * Service     : SNMPTrap                                                                           *
   * Methods     : 3                                                                                  *
   ************************************************************************************************** */
  /* snmptrap/service.proto */
  rpc intri-snmptrap-SetUsersConfig {
    input  {
      uses intri-access:UsersConfig;
    }
  }
  /* snmptrap/service.proto */
  rpc intri-snmptrap-SetEngineID {
    input  {
      uses intri-userinterface:SNMPConfig;
    }
  }
  /* snmptrap/service.proto */
  rpc intri-snmptrap-GetTrapCounters {
    output  {
      uses SNMPTrapCounter;
    }
  }

}
