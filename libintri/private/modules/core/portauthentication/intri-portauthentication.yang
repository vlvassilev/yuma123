module intri-portauthentication {
  namespace "intri:intri-portauthentication";
  prefix "intri-portauthentication";
  import portauthenticationpb {
    prefix "portauthenticationpb";
  }
  organization "Intrising Inc.";
  contact "xxx@intrising.com.tw";
  revision 2022-06-14 {
    description "Build date.";
  }
}
