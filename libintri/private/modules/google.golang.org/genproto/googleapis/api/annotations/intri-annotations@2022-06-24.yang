module intri-annotations {

  namespace "intri:intri-annotations";
  prefix "intri-annotations";
  organization "
    Intrising Inc.";
  contact "
    intrising@intrising.com.tw";
  revision 2022-06-24 {
    description "Build date.";
  }

  grouping Http {
    container Rules {
      list Rules_Entry {
        uses HttpRule;
      }
    }
    leaf FullyDecodeReservedExpansion {
      mandatory "true";
      type boolean;
    }
  }
  grouping HttpRule {
    leaf Selector {
      mandatory "true";
      type string;
    }
    choice Pattern {
    mandatory "true";
      leaf Get {
        mandatory "true";
        type string;
      }
      leaf Put {
        mandatory "true";
        type string;
      }
      leaf Post {
        mandatory "true";
        type string;
      }
      leaf Delete {
        mandatory "true";
        type string;
      }
      leaf Patch {
        mandatory "true";
        type string;
      }
      container Custom {
        uses CustomHttpPattern;
      }
    }
    leaf Body {
      mandatory "true";
      type string;
    }
    leaf ResponseBody {
      mandatory "true";
      type string;
    }
    container AdditionalBindings {
      list AdditionalBindings_Entry {
        uses HttpRule;
      }
    }
  }
  grouping CustomHttpPattern {
    leaf Kind {
      mandatory "true";
      type string;
    }
    leaf Path {
      mandatory "true";
      type string;
    }
  }
}
