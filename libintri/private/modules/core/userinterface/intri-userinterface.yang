module intri-userinterface {
  namespace "intri:intri-userinterface";
  prefix "intri-userinterface";
  import userinterfacepb {
    prefix "userinterfacepb";
  }
  organization "Intrising Inc.";
  contact "xxx@intrising.com.tw";
  revision 2022-06-14 {
    description "Build date.";
  }
}
