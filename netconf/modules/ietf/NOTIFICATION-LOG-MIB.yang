/*
 * This module has been generated by smidump 0.4.6:
 *
 *      smidump -f yang --yang-smi-extensions NOTIFICATION-LOG-MIB
 *
 * Do not edit. Edit the source file instead!
 */

module NOTIFICATION-LOG-MIB {

   /*** NAMESPACE / PREFIX DEFINITION ***/

   namespace "urn:ietf:params:xml:ns:yang:smiv2:NOTIFICATION-LOG-MIB";
   prefix "notification-log";

   /*** LINKAGE (IMPORTS / INCLUDES) ***/

   import SNMP-FRAMEWORK-MIB { prefix "snmp-framework"; }
   import SNMPv2-TC          { prefix "smiv2"; }
   import inet-types         { prefix "inet"; }
   import yang-smi           { prefix "smi"; }
   import yang-types         { prefix "yang"; }

   /*** META INFORMATION ***/

   organization     
     "IETF Distributed Management Working Group";

   contact          
     "Ramanathan Kavasseri
      Cisco Systems, Inc.
      170 West Tasman Drive,
      San Jose CA 95134-1706.
      Phone: +1 408 527 2446
      Email: ramk@cisco.com";

   description      
     "The MIB module for logging SNMP Notifications, that is, Traps
      
      
      and Informs.";

   revision "2000-11-27" {
      description   
        "This is the initial version of this MIB.
         Published as RFC 3014";
   }

   container nlmConfig {

      leaf nlmConfigGlobalEntryLimit {
         type uint32;
         config true;
         description 
           "The maximum number of notification entries that may be held
            in nlmLogTable for all nlmLogNames added together.  A particular
            setting does not guarantee that much data can be held.
            
            If an application changes the limit while there are
            Notifications in the log, the oldest Notifications MUST be
            discarded to bring the log down to the new limit - thus the
            value of nlmConfigGlobalEntryLimit MUST take precedence over
            the values of nlmConfigGlobalAgeOut and nlmConfigLogEntryLimit,
            even if the Notification being discarded has been present for
            fewer minutes than the value of nlmConfigGlobalAgeOut, or if
            the named log has fewer entries than that specified in
            nlmConfigLogEntryLimit.
            
            A value of 0 means no limit.
            
            Please be aware that contention between multiple managers
            trying to set this object to different values MAY affect the
            reliability and completeness of data seen by each manager.";
         smi:default "0";
         smi:oid "1.3.6.1.2.1.92.1.1.1";
      }

      leaf nlmConfigGlobalAgeOut {
         type uint32;
         units "minutes";
         config true;
         description 
           "The number of minutes a Notification SHOULD be kept in a log
            before it is automatically removed.
            
            If an application changes the value of nlmConfigGlobalAgeOut,
            Notifications older than the new time MAY be discarded to meet the
            new time.
            
            A value of 0 means no age out.
            
            Please be aware that contention between multiple managers
            trying to set this object to different values MAY affect the
            reliability and completeness of data seen by each manager.";
         smi:default "1440";
         smi:oid "1.3.6.1.2.1.92.1.1.2";
      }


      /* XXX table comments here XXX */

      list nlmConfigLogEntry {

         key "nlmLogName";
         description 
           "A logging control entry.  Depending on the entry's storage type
            entries may be supplied by the system or created and deleted by
            applications using nlmConfigLogEntryStatus.";
         smi:oid "1.3.6.1.2.1.92.1.1.3.1";


         leaf nlmLogName {
            type snmp-framework:SnmpAdminString {
               length "0..32";
            }
            config false;
            description   
              "The name of the log.
               
               An implementation may allow multiple named logs, up to some
               implementation-specific limit (which may be none).  A
               zero-length log name is reserved for creation and deletion by
               the managed system, and MUST be used as the default log name by
               systems that do not support named logs.";
            smi:oid "1.3.6.1.2.1.92.1.1.3.1.1";
         }

         leaf nlmConfigLogFilterName {
            type snmp-framework:SnmpAdminString {
               length "0..32";
            }
            config true;
            description   
              "A value of snmpNotifyFilterProfileName as used as an index
               into the snmpNotifyFilterTable in the SNMP Notification MIB,
               specifying the locally or remotely originated Notifications
               to be filtered out and not logged in this log.
               
               A zero-length value or a name that does not identify an
               existing entry in snmpNotifyFilterTable indicate no
               Notifications are to be logged in this log.";
            smi:default "";
            smi:oid "1.3.6.1.2.1.92.1.1.3.1.2";
         }

         leaf nlmConfigLogEntryLimit {
            type uint32;
            config true;
            description   
              "The maximum number of notification entries that can be held in
               nlmLogTable for this named log.  A particular setting does not
               guarantee that that much data can be held.
               
               If an application changes the limit while there are
               Notifications in the log, the oldest Notifications are discarded
               to bring the log down to the new limit.
               
               
               
               A value of 0 indicates no limit.
               
               Please be aware that contention between multiple managers
               trying to set this object to different values MAY affect the
               reliability and completeness of data seen by each manager.";
            smi:default "0";
            smi:oid "1.3.6.1.2.1.92.1.1.3.1.3";
         }

         leaf nlmConfigLogAdminStatus {
            type enumeration {
               enum enabled  { value 1; }
               enum disabled { value 2; }
            }
            config true;
            description   
              "Control to enable or disable the log without otherwise
               disturbing the log's entry.
               
               Please be aware that contention between multiple managers
               trying to set this object to different values MAY affect the
               reliability and completeness of data seen by each manager.";
            smi:default "enabled";
            smi:oid "1.3.6.1.2.1.92.1.1.3.1.4";
         }

         leaf nlmConfigLogOperStatus {
            type enumeration {
               enum disabled    { value 1; }
               enum operational { value 2; }
               enum noFilter    { value 3; }
            }
            config false;
            description   
              "The operational status of this log:
               
               disabled  administratively disabled
               
               operational    administratively enabled and working
               
               noFilter  administratively enabled but either
                         nlmConfigLogFilterName is zero length
                         or does not name an existing entry in
                         snmpNotifyFilterTable";
            smi:oid "1.3.6.1.2.1.92.1.1.3.1.5";
         }

         leaf nlmConfigLogStorageType {
            type smiv2:StorageType;
            config true;
            description   
              "The storage type of this conceptual row.";
            smi:oid "1.3.6.1.2.1.92.1.1.3.1.6";
         }

         leaf nlmConfigLogEntryStatus {
            type smiv2:RowStatus;
            config true;
            description   
              "Control for creating and deleting entries.  Entries may be
               modified while active.
               
               For non-null-named logs, the managed system records the security
               credentials from the request that sets nlmConfigLogStatus
               to 'active' and uses that identity to apply access control to
               the objects in the Notification to decide if that Notification
               may be logged.";
            smi:oid "1.3.6.1.2.1.92.1.1.3.1.7";
         }
      }
      smi:oid "1.3.6.1.2.1.92.1.1";
   }

   container nlmStats {

      leaf nlmStatsGlobalNotificationsLogged {
         type yang:counter32;
         units "notifications";
         config false;
         description 
           "The number of Notifications put into the nlmLogTable.  This
            counts a Notification once for each log entry, so a Notification
             put into multiple logs is counted multiple times.";
         smi:oid "1.3.6.1.2.1.92.1.2.1";
      }

      leaf nlmStatsGlobalNotificationsBumped {
         type yang:counter32;
         units "notifications";
         config false;
         description 
           "The number of log entries discarded to make room for a new entry
            due to lack of resources or the value of nlmConfigGlobalEntryLimit
            or nlmConfigLogEntryLimit.  This does not include entries discarded
            due to the value of nlmConfigGlobalAgeOut.";
         smi:oid "1.3.6.1.2.1.92.1.2.2";
      }

      smi:oid "1.3.6.1.2.1.92.1.2";
   }

   container nlmLog {


      /* XXX table comments here XXX */

      list nlmLogEntry {

         key "nlmLogName nlmLogIndex";
         description 
           "A Notification log entry.
            
            Entries appear in this table when Notifications occur and pass
            filtering by nlmConfigLogFilterName and access control.  They are
            removed to make way for new entries due to lack of resources or
            the values of nlmConfigGlobalEntryLimit, nlmConfigGlobalAgeOut, or
            nlmConfigLogEntryLimit.
            
            If adding an entry would exceed nlmConfigGlobalEntryLimit or system
            resources in general, the oldest entry in any log SHOULD be removed
            to make room for the new one.
            
            If adding an entry would exceed nlmConfigLogEntryLimit the oldest
            entry in that log SHOULD be removed to make room for the new one.
            
            Before the managed system puts a locally-generated Notification
            into a non-null-named log it assures that the creator of the log
            has access to the information in the Notification.  If not it
            does not log that Notification in that log.";
         smi:oid "1.3.6.1.2.1.92.1.3.1.1";

         leaf nlmLogName {
            type leafref {
               path "/notification-log:nlmConfig/notification-log:nlmConfigLogEntry/notification-log:nlmLogName";
            }
            config true;
            description   
              "Automagically generated leafref leaf.";
         }

         leaf nlmLogIndex {
            type uint32 {
               range "1..4294967295";
            }
            config false;
            description   
              "A monotonically increasing integer for the sole purpose of
               indexing entries within the named log.  When it reaches the
               maximum value, an extremely unlikely event, the agent wraps the
               value back to 1.";
            smi:oid "1.3.6.1.2.1.92.1.3.1.1.1";
         }

         leaf nlmLogTime {
            type yang:timestamp;
            config false;
            description   
              "The value of sysUpTime when the entry was placed in the log. If
               the entry occurred before the most recent management system
               initialization this object value MUST be set to zero.";
            smi:oid "1.3.6.1.2.1.92.1.3.1.1.2";
         }

         leaf nlmLogDateAndTime {
            type smiv2:DateAndTime;
            config false;
            description   
              "The local date and time when the entry was logged, instantiated
               only by systems that have date and time capability.";
            smi:oid "1.3.6.1.2.1.92.1.3.1.1.3";
         }

         leaf nlmLogEngineID {
            type snmp-framework:SnmpEngineID;
            config false;
            description   
              "The identification of the SNMP engine at which the Notification
               
               
               originated.
               
               If the log can contain Notifications from only one engine
               or the Trap is in SNMPv1 format, this object is a zero-length
               string.";
            smi:oid "1.3.6.1.2.1.92.1.3.1.1.4";
         }

         leaf nlmLogEngineTAddress {
            type smiv2:TAddress;
            config false;
            description   
              "The transport service address of the SNMP engine from which the
               Notification was received, formatted according to the corresponding
               value of nlmLogEngineTDomain. This is used to identify the source
               of an SNMPv1 trap, since an nlmLogEngineId cannot be extracted
               from the SNMPv1 trap pdu.
               
               This object MUST always be instantiated, even if the log
               can contain Notifications from only one engine.
               
               Please be aware that the nlmLogEngineTAddress may not uniquely
               identify the SNMP engine from which the Notification was received.
               For example, if an SNMP engine uses DHCP or NAT to obtain
               ip addresses, the address it uses may be shared with other
               network devices, and hence will not uniquely identify the
               SNMP engine.";
            smi:oid "1.3.6.1.2.1.92.1.3.1.1.5";
         }

         leaf nlmLogEngineTDomain {
            type smiv2:TDomain;
            config false;
            description   
              "Indicates the kind of transport service by which a Notification
               was received from an SNMP engine. nlmLogEngineTAddress contains
               the transport service address of the SNMP engine from which
               this Notification was received.
               
               Possible values for this object are presently found in the
               Transport Mappings for SNMPv2 document (RFC 1906 [8]).";
            smi:oid "1.3.6.1.2.1.92.1.3.1.1.6";
         }

         leaf nlmLogContextEngineID {
            type snmp-framework:SnmpEngineID;
            config false;
            description   
              "If the Notification was received in a protocol which has a
               contextEngineID element like SNMPv3, this object has that value.
               Otherwise its value is a zero-length string.";
            smi:oid "1.3.6.1.2.1.92.1.3.1.1.7";
         }

         leaf nlmLogContextName {
            type snmp-framework:SnmpAdminString;
            config false;
            description   
              "The name of the SNMP MIB context from which the Notification came.
               For SNMPv1 Traps this is the community string from the Trap.";
            smi:oid "1.3.6.1.2.1.92.1.3.1.1.8";
         }

         leaf nlmLogNotificationID {
            type yang:object-identifier;
            config false;
            description   
              "The NOTIFICATION-TYPE object identifier of the Notification that
               occurred.";
            smi:oid "1.3.6.1.2.1.92.1.3.1.1.9";
         }
      }


      /* XXX table comments here XXX */

      list nlmLogVariableEntry {

         key "nlmLogName nlmLogIndex nlmLogVariableIndex";
         description 
           "A Notification log entry variable.
            
            Entries appear in this table when there are variables in
            the varbind list of a Notification in nlmLogTable.";
         smi:oid "1.3.6.1.2.1.92.1.3.2.1";

         leaf nlmLogName {
            type leafref {
               path "/notification-log:nlmConfig/notification-log:nlmConfigLogEntry/notification-log:nlmLogName";
            }
            config true;
            description   
              "Automagically generated leafref leaf.";
         }
         leaf nlmLogIndex {
            type leafref {
               path "/notification-log:nlmLog/notification-log:nlmLogEntry/notification-log:nlmLogIndex";
            }
            config false;
            description   
              "Automagically generated leafref leaf.";
         }

         leaf nlmLogVariableIndex {
            type uint32 {
               range "1..4294967295";
            }
            config false;
            description   
              "A monotonically increasing integer, starting at 1 for a given
               nlmLogIndex, for indexing variables within the logged
               Notification.";
            smi:oid "1.3.6.1.2.1.92.1.3.2.1.1";
         }

         leaf nlmLogVariableID {
            type yang:object-identifier;
            config false;
            description   
              "The variable's object identifier.";
            smi:oid "1.3.6.1.2.1.92.1.3.2.1.2";
         }

         leaf nlmLogVariableValueType {
            type enumeration {
               enum counter32   { value 1; }
               enum unsigned32  { value 2; }
               enum timeTicks   { value 3; }
               enum integer32   { value 4; }
               enum ipAddress   { value 5; }
               enum octetString { value 6; }
               enum objectId    { value 7; }
               enum counter64   { value 8; }
               enum opaque      { value 9; }
            }
            config false;
            description   
              "The type of the value.  One and only one of the value
               objects that follow must be instantiated, based on this type.";
            smi:oid "1.3.6.1.2.1.92.1.3.2.1.3";
         }

         leaf nlmLogVariableCounter32Val {
            type yang:counter32;
            config false;
            description   
              "The value when nlmLogVariableType is 'counter32'.";
            smi:oid "1.3.6.1.2.1.92.1.3.2.1.4";
         }

         leaf nlmLogVariableUnsigned32Val {
            type uint32;
            config false;
            description   
              "The value when nlmLogVariableType is 'unsigned32'.";
            smi:oid "1.3.6.1.2.1.92.1.3.2.1.5";
         }

         leaf nlmLogVariableTimeTicksVal {
            type yang:timeticks;
            config false;
            description   
              "The value when nlmLogVariableType is 'timeTicks'.";
            smi:oid "1.3.6.1.2.1.92.1.3.2.1.6";
         }

         leaf nlmLogVariableInteger32Val {
            type int32;
            config false;
            description   
              "The value when nlmLogVariableType is 'integer32'.";
            smi:oid "1.3.6.1.2.1.92.1.3.2.1.7";
         }

         leaf nlmLogVariableOctetStringVal {
            type binary;
            config false;
            description   
              "The value when nlmLogVariableType is 'octetString'.";
            smi:oid "1.3.6.1.2.1.92.1.3.2.1.8";
         }

         leaf nlmLogVariableIpAddressVal {
            type inet:ipv4-address;
            config false;
            description   
              "The value when nlmLogVariableType is 'ipAddress'.
               Although this seems to be unfriendly for IPv6, we
               have to recognize that there are a number of older
               MIBs that do contain an IPv4 format address, known
               as IpAddress.
               
               IPv6 addresses are represented using TAddress or
               InetAddress, and so the underlying datatype is
               
               
               OCTET STRING, and their value would be stored in
               the nlmLogVariableOctetStringVal column.";
            smi:oid "1.3.6.1.2.1.92.1.3.2.1.9";
         }

         leaf nlmLogVariableOidVal {
            type yang:object-identifier;
            config false;
            description   
              "The value when nlmLogVariableType is 'objectId'.";
            smi:oid "1.3.6.1.2.1.92.1.3.2.1.10";
         }

         leaf nlmLogVariableCounter64Val {
            type yang:counter64;
            config false;
            description   
              "The value when nlmLogVariableType is 'counter64'.";
            smi:oid "1.3.6.1.2.1.92.1.3.2.1.11";
         }

         leaf nlmLogVariableOpaqueVal {
            type binary;
            config false;
            description   
              "The value when nlmLogVariableType is 'opaque'.";
            smi:oid "1.3.6.1.2.1.92.1.3.2.1.12";
         }
      }
      smi:oid "1.3.6.1.2.1.92.1.3";
   }


   /* XXX table comments here XXX */

   augment "/notification-log:nlmConfig/notification-log:nlmConfigLogEntry" {
      description   
        "A Notification log statistics entry.";

      leaf nlmStatsLogNotificationsLogged {
         type yang:counter32;
         units "notifications";
         config false;
         description 
           "The number of Notifications put in this named log.";
         smi:oid "1.3.6.1.2.1.92.1.2.3.1.1";
      }

      leaf nlmStatsLogNotificationsBumped {
         type yang:counter32;
         units "notifications";
         config false;
         description 
           "The number of log entries discarded from this named log to make
            room for a new entry due to lack of resources or the value of
            nlmConfigGlobalEntryLimit or nlmConfigLogEntryLimit.  This does not
            include entries discarded due to the value of
            nlmConfigGlobalAgeOut.";
         smi:oid "1.3.6.1.2.1.92.1.2.3.1.2";
      }
      smi:oid "1.3.6.1.2.1.92.1.2.3.1";
   }

} /* end of module NOTIFICATION-LOG-MIB */
