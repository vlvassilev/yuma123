submodule intri-loop-msg {
  belongs-to "intri-loop" {
    prefix "intri-loop-msg";
  }
  include intri-loop-enum;
  import protobufpb {
    prefix "protobufpb";
  }
  import looppb {
    prefix "looppb";
  }
  import devicepb {
    prefix "devicepb";
  }
  revision 2022-06-14 {
    description "Build date.";
  }
  // core/loop/loop.proto
  grouping Config {
    container Config_PortList {
      uses looppb:PortConfigEntry;
    }
  }
  // core/loop/loop.proto
  grouping PortConfigEntry {
    container PortConfigEntry_IdentifyNo {
      uses devicepb:InterfaceIdentify;
    }
    leaf PortConfigEntry_Enabled {
      type boolean;
    }
  }
  // core/loop/loop.proto
  grouping PortConfig {
    container PortConfig_List {
      uses looppb:PortConfigEntry;
    }
  }
  // core/loop/loop.proto
  grouping StatusEntry {
    container StatusEntry_IdentifyNo {
      uses devicepb:InterfaceIdentify;
    }
    container StatusEntry_LastLoopTs {
      uses protobufpb:Timestamp;
    }
    leaf StatusEntry_LoopCount {
      type int32;
    }
    leaf StatusEntry_IsLoopCurrent {
      type boolean;
    }
  }
  // core/loop/loop.proto
  grouping Status {
    container Status_List {
      uses looppb:StatusEntry;
    }
  }
}
