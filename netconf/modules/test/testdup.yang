module testdup {

    namespace "http://netconfcentral.com/ns/testdup";
    prefix "t";

    organization
        "Netconf Central";

    contact
        "Andy Bierman";

    description
        "YANG duplicates test module.";

    revision 2009-03-08 {
        description "Initial version.";
    }

    leaf instance1 {
       type instance-identifier;
    }

    leaf instance2 {
       type instance-identifier {
          require-instance false;
       }
    }


}
