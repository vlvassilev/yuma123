module intri-sfp {

  namespace "intri:intri-sfp";
  prefix "intri-sfp";
  organization "
    Intrising Inc.";
  contact "
    intrising@intrising.com.tw";
  revision 2022-06-24 {
    description "Build date.";
  }

  import intri-event {
    prefix intri-event;
  }
  import intri-empty {
    prefix intri-empty;
  }
  grouping Config {
    leaf LossOfSignalEvent {
      mandatory "true";
      type boolean;
    }
  }
  grouping Info {
    container List {
      list List_Entry {
        uses intri-event:SFPInfo;
      }
    }
  }
  rpc intri-sfp-SFP-GetConfig {
    output {
      uses Config;
    }
  }
  rpc intri-sfp-SFP-SetConfig {
    input {
      uses Config;
    }
  }
  rpc intri-sfp-SFP-GetStatus {
    output {
      uses Info;
    }
  }
}
