// Code generated by protoc-gen-yang. DO NOT EDIT.


/* ****************************************************************************************************
 * Import Path : "github.com/Intrising/intri-type/core/diagnostic"                                    *
 * Dir Path    : github.com/Intrising/intri-type/core/diagnostic                                      *
 * Go Package  : diagnostic                                                                           *
 * Files       : 2                                                                                    *
 **************************************************************************************************** */
module intri-diagnostic {

  namespace "intri:intri-diagnostic";

  prefix "intri-diagnostic";

  organization "Intrising Inc.";

  contact "intrising@intrising.com.tw";

  revision 2022-06-23 {
    description "Build date.";
  }

  import intri-common {
    prefix intri-common;
  }
  import intri-empty {
    prefix intri-empty;
  }


  /* **************************************************************************************************
   * Msgs        : 2                                                                                  *
   ************************************************************************************************** */
  /* core/diagnostic/diagnostic.proto */
  grouping ARPEntry {
    leaf IPAddr {
      type string;
    }
    leaf MACAddr {
      type string;
    }
  }
  /* core/diagnostic/diagnostic.proto */
  grouping ARPTables {
    container List {
      list List_Entry {
        uses ARPEntry;
      }
    }
  }


  /* **************************************************************************************************
   * Services    : 1                                                                                  *
   ************************************************************************************************** */

  /* **************************************************************************************************
   * Service     : Diagnostic                                                                         *
   * Methods     : 4                                                                                  *
   ************************************************************************************************** */
  /* core/diagnostic/service.proto */
  rpc intri-diagnostic-RunPingTest {
    input  {
      uses intri-common:IPAddress;
    }
    output  {
      uses intri-common:Reply;
    }
  }
  /* core/diagnostic/service.proto */
  rpc intri-diagnostic-RunTraceRoute {
    input  {
      uses intri-common:IPAddress;
    }
    output  {
      uses intri-common:Reply;
    }
  }
  /* core/diagnostic/service.proto */
  rpc intri-diagnostic-RunDNSLookup {
    input  {
      uses intri-common:Name;
    }
    output  {
      uses intri-common:Reply;
    }
  }
  /* core/diagnostic/service.proto */
  rpc intri-diagnostic-GetARPTable {
    output  {
      uses ARPTables;
    }
  }

}
