submodule intri-log-msg {
  belongs-to "intri-log" {
    prefix "intri-log-msg";
  }
  include intri-log-enum;
  import logpb {
    prefix "logpb";
  }
  import eventpb {
    prefix "eventpb";
  }
  import protobufpb {
    prefix "protobufpb";
  }
  revision 2022-06-14 {
    description "Build date.";
  }
  // log/log.proto
  grouping Config {
    container Config_BasicConfig {
      uses logpb:BasicConfig;
    }
    container Config_TargetConfig {
      uses logpb:TargetConfig;
    }
    container Config_ActionConfig {
      uses logpb:ActionConfig;
    }
  }
  // log/log.proto
  grouping BasicConfig {
    leaf BasicConfig_StorageOption {
      type logpb:StorageTypeOptions;
    }
  }
  // log/log.proto
  grouping TargetConfig {
    container TargetConfig_List {
      uses logpb:TargetConfigEntry;
    }
  }
  // log/log.proto
  grouping TargetConfigEntry {
    leaf TargetConfigEntry_Name {
      type string;
    }
    leaf TargetConfigEntry_HostAddress {
      type string;
    }
    leaf TargetConfigEntry_TargetLogType {
      type eventpb:TargetLogTypeOptions;
    }
    leaf TargetConfigEntry_LoggingSeverityType {
      type eventpb:LoggingSeverityTypeOptions;
    }
    leaf TargetConfigEntry_LogConfigChanges {
      type boolean;
    }
    leaf TargetConfigEntry_LogDebugEventOnly {
      type boolean;
    }
    leaf TargetConfigEntry_SnmpV3Username {
      type string;
    }
    leaf TargetConfigEntry_SnmpTrapCommunity {
      type string;
    }
  }
  // log/log.proto
  grouping ActionConfig {
    container ActionConfig_List {
      uses logpb:ActionConfigEntry;
    }
  }
  // log/log.proto
  grouping ActionConfigEntry {
    leaf ActionConfigEntry_LoggingType {
      type eventpb:LoggingTypeOptions;
    }
    leaf ActionConfigEntry_LoggingSeverityType {
      type eventpb:LoggingSeverityTypeOptions;
    }
  }
  // log/log.proto
  grouping Statistics {
    leaf Statistics_NumberOfTargets {
      type uint64;
    }
    leaf Statistics_SyslogCounter {
      type int32;
    }
    leaf Statistics_SnmpTrapCounter {
      type int32;
    }
    leaf Statistics_SnmpInfoCounter {
      type int32;
    }
    leaf Statistics_DisplayInCliCounter {
      type int32;
    }
  }
  // log/log.proto
  grouping LogFileEntry {
    leaf LogFileEntry_LogID {
      type uint64;
    }
    container LogFileEntry_Ts {
      uses protobufpb:Timestamp;
    }
    leaf LogFileEntry_LoggingType {
      type eventpb:LoggingTypeOptions;
    }
    leaf LogFileEntry_LoggingSeverityType {
      type eventpb:LoggingSeverityTypeOptions;
    }
    leaf LogFileEntry_Message {
      type string;
    }
  }
  // log/log.proto
  grouping LogFiles {
    container LogFiles_List {
      uses logpb:LogFileEntry;
    }
  }
}
