module ietf-netconf-partial-lock {

  namespace urn:ietf:params:xml:ns:netconf:partial-lock:1.0;
  prefix pl;
  import yuma-ncx { prefix ncx; }

  organization "IETF Network Configuration (netconf) Working Group";

  contact
   "Netconf Working Group
    Mailing list: netconf@ietf.org
    Web: http://www.ietf.org/html.charters/netconf-charter.html

    Balazs Lengyel
    Ericsson
    balazs.lengyel@ericsson.com";

  description
   "This YANG module defines the <partial-lock> and
    <partial-unlock> operations.";

  revision 2009-02-19 {
    description
     "Initial version, published as RFC yyyy.";
     // RFC Ed.: replace yyyy with actual RFC number & remove this note.
  }

  typedef lock-id-type {
    type uint32;
    description
     "A number identifying a specific partial-lock granted to a session.
      It is allocated by the system, and SHOULD be used in the
      partial-unlock operation.";
  }

  rpc partial-lock {
    description
     "A NETCONF operation that locks part of one or more datastores.";
    input {
      list target {
        min-elements 1;
        description
         "A list of one or more datastore names.
          Each list entry must contain a different datastore name.";
        choice datastore {
          leaf running   { type empty; }
          leaf candidate { type empty; }
          leaf startup   { type empty; }
        }
      }
      leaf-list select {
        type string {
	    ncx:xpath;
        }
        min-elements 1;
        description
         "XPath expression that specifies the scope of the lock.
          An Instance Identifier expression MUST be used unless the
          :xpath capability is supported, in which case any XPath 1.0
          expression is allowed.";
      }
    }
    output {
      leaf lock-id {
        type lock-id-type;
        description
         "Identifies the lock, if granted. The lock-id SHOULD be
          used in the partial-unlock rpc.";
      }
      container running {
        leaf-list locked-node {
          type instance-identifier;
          min-elements 1;
          description
           "List of locked nodes in the running datastore";
        }
      }
      container candidate {
        leaf-list locked-node {
          type instance-identifier;
          min-elements 1;
          description
           "List of locked nodes in the candidate datastore";
        }
      }
      container startup {
        leaf-list locked-node {
          type instance-identifier;
          min-elements 1;
          description
           "List of locked nodes in the startup datastore";
        }
      }
    }
  }

  rpc partial-unlock {
    description
     "A NETCONF operation that releases a previously acquired
      partial-lock.";
    input {
      leaf lock-id {
        type lock-id-type;
        description
         "Identifies the lock to be released. MUST be the value
          received in the response to the partial-lock operation.";
      }
    }
  }
}
