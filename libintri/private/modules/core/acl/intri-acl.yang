module intri-acl {
  namespace "intri:intri-acl";
  prefix "intri-acl";
  import aclpb {
    prefix "aclpb";
  }
  organization "Intrising Inc.";
  contact "xxx@intrising.com.tw";
  revision 2022-06-14 {
    description "Build date.";
  }
}
