module intri-snmptrap {
  namespace "intri:intri-snmptrap";
  prefix "intri-snmptrap";
  organization "Intrising Inc.";
  contact "xxx@intrising.com.tw";
  revision 2022-06-14 {
    description "Build date.";
  }
}
