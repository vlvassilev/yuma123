// Code generated by protoc-gen-yang. DO NOT EDIT.


/* ****************************************************************************************************
 * Import Path : "github.com/Intrising/intri-type/core/timesync"                                      *
 * Dir Path    : github.com/Intrising/intri-type/core/timesync                                        *
 * Go Package  : timesync                                                                             *
 * Files       : 2                                                                                    *
 **************************************************************************************************** */
module intri-timesync {

  namespace "intri:intri-timesync";

  prefix "intri-timesync";

  organization "Intrising Inc.";

  contact "intrising@intrising.com.tw";

  revision 2022-06-23 {
    description "Build date.";
  }

  import intri-device {
    prefix intri-device;
  }
  import intri-empty {
    prefix intri-empty;
  }


  /* **************************************************************************************************
   * Enums       : 6                                                                                  *
   ************************************************************************************************** */
  /* core/timesync/timesync.proto */
  typedef SyncEModeTypeOptions {
    type enumeration {
      enum SYNCE_MODE_TYPE_DISABLED {
        description "[Disabled]";
        value 0;
      }
      enum SYNCE_MODE_TYPE_STATIC {
        description "[Static]";
        value 1;
      }
      enum SYNCE_MODE_TYPE_ESMC {
        description "[ESMC]";
        value 2;
      }
    }
  }
  /* core/timesync/timesync.proto */
  typedef SyncSourceTypeOptions {
    type enumeration {
      enum SYNC_SOURCE_TYPE_GNSS {
        description "[GNSS]";
        value 0;
      }
      enum SYNC_SOURCE_TYPE_SYNCE {
        description "[SyncE]";
        value 1;
      }
      enum SYNC_SOURCE_TYPE_10MHZ_INPUT {
        description "[10MHz Input]";
        value 2;
      }
      enum SYNC_SOURCE_TYPE_1PPS_INPUT {
        description "[1PPS Input]";
        value 3;
      }
      enum SYNC_SOURCE_TYPE_BITS_INPUT {
        description "[BITS Input]";
        value 4;
      }
      enum SYNC_SOURCE_TYPE_PTP {
        description "[PTP]";
        value 5;
      }
    }
  }
  /* core/timesync/timesync.proto */
  typedef LockStatusTypeOptions {
    type enumeration {
      enum LOCK_STATUS_TYPE_FREERUN {
        description "[FreeRun]";
        value 0;
      }
      enum LOCK_STATUS_TYPE_LOCK_ACQUISITION {
        description "[Lock Acquisition]";
        value 1;
      }
      enum LOCK_STATUS_TYPE_LOCKED {
        description "[Locked]";
        value 2;
      }
      enum LOCK_STATUS_TYPE_HOLDOVER {
        description "[Holdover]";
        value 3;
      }
    }
  }
  /* core/timesync/timesync.proto */
  typedef SignalTypeOptions {
    type enumeration {
      enum SIGNAL_TYPE_OK {
        description "[OK]";
        value 0;
      }
      enum SIGNAL_TYPE_LOSS {
        description "[Loss]";
        value 1;
      }
    }
  }
  /* core/timesync/timesync.proto */
  typedef ToDMessageTypeOptions {
    type enumeration {
      enum TOD_MESSAGE_TYPE_NMEA_GPZDA {
        description "[NMEA GPZDA]";
        value 0;
      }
    }
  }
  /* core/timesync/timesync.proto */
  typedef GNSSStateTypeOptions {
    type enumeration {
      enum GNSS_STATE_TYPE_DISABLE {
        description "[Disable]";
        value 0;
      }
      enum GNSS_STATE_TYPE_SYNC {
        description "[Sync]";
        value 1;
      }
      enum GNSS_STATE_TYPE_TRACKING {
        description "[Tracking]";
        value 2;
      }
    }
  }


  /* **************************************************************************************************
   * Msgs        : 10                                                                                 *
   ************************************************************************************************** */
  /* core/timesync/timesync.proto */
  grouping Config {
    container GNSS {
      uses GNSSConfig;
    }
    container SyncE {
      uses SyncEConfig;
    }
    container SyncSource {
      uses SyncSourceConfig;
    }
    container Reference {
      uses ReferenceOutput;
    }
  }
  /* core/timesync/timesync.proto */
  grouping GNSSConfig {
    leaf Enabled {
      type boolean;
    }
  }
  /* core/timesync/timesync.proto */
  grouping SyncEConfig {
    leaf Mode {
      type SyncEModeTypeOptions;
    }
    container ReferenceIdentifyNo {
      uses intri-device:InterfaceIdentify;
    }
  }
  /* core/timesync/timesync.proto */
  grouping SyncSourceConfig {
    leaf Source {
      type SyncSourceTypeOptions;
    }
  }
  /* core/timesync/timesync.proto */
  grouping ReferenceOutput {
    container Tod {
      uses ToDConfig;
    }
  }
  /* core/timesync/timesync.proto */
  grouping ToDConfig {
    leaf Enabled {
      type boolean;
    }
    leaf MessageType {
      type ToDMessageTypeOptions;
    }
  }
  /* core/timesync/timesync.proto */
  grouping GNSStatus {
    leaf State {
      type GNSSStateTypeOptions;
    }
    leaf Longitude {
      type string;
    }
    leaf Latitude {
      type string;
    }
    leaf DateTime {
      type string;
    }
  }
  /* core/timesync/timesync.proto */
  grouping SyncEStatus {
    container ReferenceIdentifyNo {
      uses intri-device:InterfaceIdentify;
    }
    leaf Signal {
      type SignalTypeOptions;
    }
    leaf LockStatus {
      type LockStatusTypeOptions;
    }
  }
  /* core/timesync/timesync.proto */
  grouping SyncSourceStatus {
    leaf LockStatus {
      type LockStatusTypeOptions;
    }
    container List {
      list List_Entry {
        uses SyncSourceInputStatusEntry;
      }
    }
  }
  /* core/timesync/timesync.proto */
  grouping SyncSourceInputStatusEntry {
    leaf Source {
      type SyncSourceTypeOptions;
    }
    leaf Signal {
      type SignalTypeOptions;
    }
  }


  /* **************************************************************************************************
   * Services    : 1                                                                                  *
   ************************************************************************************************** */

  /* **************************************************************************************************
   * Service     : TimeSync                                                                           *
   * Methods     : 11                                                                                 *
   ************************************************************************************************** */
  /* core/timesync/service.proto */
  rpc intri-timesync-SetGNSSConfig {
    input  {
      uses GNSSConfig;
    }
  }
  /* core/timesync/service.proto */
  rpc intri-timesync-GetGNSSConfig {
    output  {
      uses GNSSConfig;
    }
  }
  /* core/timesync/service.proto */
  rpc intri-timesync-GetGNSSStatus {
    output  {
      uses GNSStatus;
    }
  }
  /* core/timesync/service.proto */
  rpc intri-timesync-SetSyncEConfig {
    input  {
      uses SyncEConfig;
    }
  }
  /* core/timesync/service.proto */
  rpc intri-timesync-GetSyncEConfig {
    output  {
      uses SyncEConfig;
    }
  }
  /* core/timesync/service.proto */
  rpc intri-timesync-GetSyncEStatus {
    output  {
      uses SyncEStatus;
    }
  }
  /* core/timesync/service.proto */
  rpc intri-timesync-SetSyncSourceConfig {
    input  {
      uses SyncSourceConfig;
    }
  }
  /* core/timesync/service.proto */
  rpc intri-timesync-GetSyncSourceConfig {
    output  {
      uses SyncSourceConfig;
    }
  }
  /* core/timesync/service.proto */
  rpc intri-timesync-GetSyncSourceStatus {
    output  {
      uses SyncSourceStatus;
    }
  }
  /* core/timesync/service.proto */
  rpc intri-timesync-SetReferenceOutput {
    input  {
      uses ReferenceOutput;
    }
  }
  /* core/timesync/service.proto */
  rpc intri-timesync-GetReferenceOutput {
    output  {
      uses ReferenceOutput;
    }
  }

}
