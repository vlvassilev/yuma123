// Code generated by protoc-gen-yang. DO NOT EDIT.


/* ****************************************************************************************************
 * Import Path : "github.com/Intrising/intri-type/core/loop"                                          *
 * Dir Path    : github.com/Intrising/intri-type/core/loop                                            *
 * Go Package  : loop                                                                                 *
 * Files       : 2                                                                                    *
 **************************************************************************************************** */
module intri-loop {

  namespace "intri:intri-loop";

  prefix "intri-loop";

  organization "Intrising Inc.";

  contact "intrising@intrising.com.tw";

  revision 2022-06-23 {
    description "Build date.";
  }

  import intri-device {
    prefix intri-device;
  }
  import intri-timestamp {
    prefix intri-timestamp;
  }
  import intri-empty {
    prefix intri-empty;
  }


  /* **************************************************************************************************
   * Msgs        : 5                                                                                  *
   ************************************************************************************************** */
  /* core/loop/loop.proto */
  grouping Config {
    container PortList {
      list PortList_Entry {
        uses PortConfigEntry;
      }
    }
  }
  /* core/loop/loop.proto */
  grouping PortConfigEntry {
    container IdentifyNo {
      uses intri-device:InterfaceIdentify;
    }
    leaf Enabled {
      type boolean;
    }
  }
  /* core/loop/loop.proto */
  grouping PortConfig {
    container List {
      list List_Entry {
        uses PortConfigEntry;
      }
    }
  }
  /* core/loop/loop.proto */
  grouping StatusEntry {
    container IdentifyNo {
      uses intri-device:InterfaceIdentify;
    }
    container LastLoopTs {
      uses intri-timestamp:Timestamp;
    }
    leaf LoopCount {
      type int32;
    }
    leaf IsLoopCurrent {
      type boolean;
    }
  }
  /* core/loop/loop.proto */
  grouping Status {
    container List {
      list List_Entry {
        uses StatusEntry;
      }
    }
  }


  /* **************************************************************************************************
   * Services    : 1                                                                                  *
   ************************************************************************************************** */

  /* **************************************************************************************************
   * Service     : Loop                                                                               *
   * Methods     : 4                                                                                  *
   ************************************************************************************************** */
  /* core/loop/service.proto */
  rpc intri-loop-GetStatus {
    output  {
      uses Status;
    }
  }
  /* core/loop/service.proto */
  rpc intri-loop-GetConfig {
    output  {
      uses Config;
    }
  }
  /* core/loop/service.proto */
  rpc intri-loop-GetPortConfig {
    output  {
      uses PortConfig;
    }
  }
  /* core/loop/service.proto */
  rpc intri-loop-UpdatePortConfig {
    input  {
      uses PortConfigEntry;
    }
  }

}
