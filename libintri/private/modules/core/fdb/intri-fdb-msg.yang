submodule intri-fdb-msg {
  belongs-to "intri-fdb" {
    prefix "intri-fdb-msg";
  }
  include intri-fdb-enum;
  import fdbpb {
    prefix "fdbpb";
  }
  import devicepb {
    prefix "devicepb";
  }
  revision 2022-06-14 {
    description "Build date.";
  }
  // core/fdb/fdb.proto
  grouping Config {
    container Config_AgeTime {
      uses fdbpb:AgingTime;
    }
    container Config_PortLimit {
      uses fdbpb:PortLearningLimit;
    }
    container Config_ForwardConfig {
      uses fdbpb:ForwardConfig;
    }
    container Config_DropConfig {
      uses fdbpb:DropConfig;
    }
  }
  // core/fdb/fdb.proto
  grouping AgingTime {
    leaf AgingTime_GlobalAgingTime {
      type int32;
    }
  }
  // core/fdb/fdb.proto
  grouping ForwardConfig {
    container ForwardConfig_List {
      uses fdbpb:ForwardConfigEntry;
    }
  }
  // core/fdb/fdb.proto
  grouping ForwardConfigEntry {
    leaf ForwardConfigEntry_MACAddress {
      type string;
    }
    leaf ForwardConfigEntry_VlanID {
      type int32;
    }
    container ForwardConfigEntry_IdentifyNo {
      uses devicepb:InterfaceIdentify;
    }
  }
  // core/fdb/fdb.proto
  grouping DropConfig {
    container DropConfig_List {
      uses fdbpb:DropConfigEntry;
    }
  }
  // core/fdb/fdb.proto
  grouping DropConfigEntry {
    leaf DropConfigEntry_MACAddress {
      type string;
    }
    leaf DropConfigEntry_VlanID {
      type int32;
    }
    container DropConfigEntry_IdentifyNo {
      uses devicepb:InterfaceIdentify;
    }
  }
  // core/fdb/fdb.proto
  grouping PortLearningLimit {
    container PortLearningLimit_List {
      uses fdbpb:PortLearningLimitEntry;
    }
  }
  // core/fdb/fdb.proto
  grouping PortLearningLimitEntry {
    container PortLearningLimitEntry_IdentifyNo {
      uses devicepb:InterfaceIdentify;
    }
    leaf PortLearningLimitEntry_Limit {
      type int32;
    }
  }
  // core/fdb/fdb.proto
  grouping Info {
    leaf Info_UsedAgingTime {
      type int32;
    }
    leaf Info_NumberOfFreeEntries {
      type int32;
    }
    leaf Info_NumberOfUsedEntries {
      type int32;
    }
    leaf Info_NumberOfMacUnicastDynamicEntries {
      type int32;
    }
    leaf Info_NumberOfMacUnicastStaticEntries {
      type int32;
    }
    leaf Info_NumberOfMacMulticastDynamicEntries {
      type int32;
    }
    leaf Info_NumberOfMacMulticastStaticEntries {
      type int32;
    }
    leaf Info_NumberOfIpv4MulticastEntries {
      type int32;
    }
    leaf Info_NumberOfIpv6MulticastEntries {
      type int32;
    }
  }
  // core/fdb/fdb.proto
  grouping Status {
    container Status_List {
      uses fdbpb:StatusEntry;
    }
  }
  // core/fdb/fdb.proto
  grouping StatusEntry {
    leaf StatusEntry_VlanID {
      type int32;
    }
    leaf StatusEntry_MACAddress {
      type string;
    }
    container StatusEntry_IdentifyNo {
      uses devicepb:InterfaceIdentify;
    }
    leaf StatusEntry_State {
      type fdbpb:MACTableStateTypeOptions;
    }
  }
  // core/fdb/fdb.proto
  grouping SpecificMac {
    leaf SpecificMac_MACAddress {
      type string;
    }
  }
  // core/fdb/fdb.proto
  grouping FlushOption {
    leaf FlushOption_DynamicAll {
      type boolean;
    }
    container FlushOption_Identify {
      uses devicepb:PortList;
    }
  }
  // core/fdb/fdb.proto
  grouping PortOccupied {
    container PortOccupied_IdentifyNo {
      uses devicepb:InterfaceIdentify;
    }
    leaf PortOccupied_Type {
      type fdbpb:PortOccupiedTypeOptions;
    }
  }
}
