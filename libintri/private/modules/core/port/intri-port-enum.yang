submodule intri-port-enum {
  belongs-to "intri-port" {
    prefix "intri-port-enum";
  }
  revision 2022-06-14 {
    description "Build date.";
  }
  // core/port/port.proto
  typedef LinkStateTypeOptions {
    type enumeration {
      enum LINK_STATE_TYPE_LINK_DOWN {
        description "[Link Down] Link is not established. No communication. Ethernet LED is off";
        value 0;
      }
      enum LINK_STATE_TYPE_BLOCKING {
        description "[Blocking] Port is blocked. No communication. Ethernet LED indicates yellow.";
        value 1;
      }
      enum LINK_STATE_TYPE_LEARNING {
        description "[Learning] Port is learning MAC addresses. No communication. Ethernet LED indicates yellow.";
        value 2;
      }
      enum LINK_STATE_TYPE_FORWARDING {
        description "[Forwarding] Port is forwarding data. Ethernet LED indicates green.";
        value 3;
      }
      enum LINK_STATE_TYPE_UNAUTH_VLAN {
        description "[Unauth VLAN] Port is forwarding data on the unauthorized_vlan only. Ethernet LED indicates green.";
        value 4;
      }
    }
  }
}
