submodule intri-monitor-msg {
  belongs-to "intri-monitor" {
    prefix "intri-monitor-msg";
  }
  include intri-monitor-enum;
  import monitorpb {
    prefix "monitorpb";
  }
  import eventpb {
    prefix "eventpb";
  }
  import devicepb {
    prefix "devicepb";
  }
  revision 2022-06-14 {
    description "Build date.";
  }
  // core/monitor/monitor.proto
  grouping Config {
    container Config_DeviceLimitConfig {
      uses monitorpb:DeviceLimitConfig;
    }
    container Config_SystemLimitConfig {
      uses monitorpb:SystemLimitConfig;
    }
  }
  // core/monitor/monitor.proto
  grouping DeviceLimitConfigEntry {
    leaf DeviceLimitConfigEntry_MonitorOption {
      type monitorpb:DeviceMonitorTypeOptions;
    }
    leaf DeviceLimitConfigEntry_LimitOption {
      type monitorpb:LimitBoundaryTypeOptions;
    }
    container DeviceLimitConfigEntry_Boundary {
      uses monitorpb:RangeValue;
    }
    leaf DeviceLimitConfigEntry_ValueOption {
      type monitorpb:ValueTypeOptions;
    }
    container DeviceLimitConfigEntry_Value {
      uses monitorpb:RangeValue;
    }
  }
  // core/monitor/monitor.proto
  grouping DeviceLimitConfig {
    container DeviceLimitConfig_List {
      uses monitorpb:DeviceLimitConfigEntry;
    }
  }
  // core/monitor/monitor.proto
  grouping SystemLimitConfigEntry {
    leaf SystemLimitConfigEntry_MonitorOption {
      type monitorpb:SystemMonitorTypeOptions;
    }
    leaf SystemLimitConfigEntry_LimitOption {
      type monitorpb:LimitBoundaryTypeOptions;
    }
    container SystemLimitConfigEntry_Boundary {
      uses monitorpb:RangeValue;
    }
    leaf SystemLimitConfigEntry_ValueOption {
      type monitorpb:ValueTypeOptions;
    }
    container SystemLimitConfigEntry_Value {
      uses monitorpb:RangeValue;
    }
  }
  // core/monitor/monitor.proto
  grouping SystemLimitConfig {
    container SystemLimitConfig_List {
      uses monitorpb:SystemLimitConfigEntry;
    }
  }
  // core/monitor/monitor.proto
  grouping RangeValue {
    leaf RangeValue_IntMin {
      type int32;
    }
    leaf RangeValue_IntMax {
      type int32;
    }
    leaf RangeValue_FloatMin {
      type decimal64 {
        fraction-digits 2;
      }
    }
    leaf RangeValue_FloatMax {
      type decimal64 {
        fraction-digits 2;
      }
    }
    leaf RangeValue_Int64Min {
      type int64;
    }
    leaf RangeValue_Int64Max {
      type int64;
    }
    leaf RangeValue_Float64Min {
      type decimal64 {
        fraction-digits 2;
      }
    }
    leaf RangeValue_Float64Max {
      type decimal64 {
        fraction-digits 2;
      }
    }
  }
  // core/monitor/monitor.proto
  grouping DeviceScorllBarValueEntry {
    leaf DeviceScorllBarValueEntry_MonitorOption {
      type monitorpb:DeviceMonitorTypeOptions;
    }
    container DeviceScorllBarValueEntry_Value {
      uses monitorpb:RangeValue;
    }
  }
  // core/monitor/monitor.proto
  grouping DeviceScorllBarValue {
    container DeviceScorllBarValue_List {
      uses monitorpb:DeviceScorllBarValueEntry;
    }
  }
  // core/monitor/monitor.proto
  grouping SystemScorllBarValueEntry {
    leaf SystemScorllBarValueEntry_MonitorOption {
      type monitorpb:SystemMonitorTypeOptions;
    }
    container SystemScorllBarValueEntry_Value {
      uses monitorpb:RangeValue;
    }
  }
  // core/monitor/monitor.proto
  grouping SystemScorllBarValue {
    container SystemScorllBarValue_List {
      uses monitorpb:SystemScorllBarValueEntry;
    }
  }
  // core/monitor/monitor.proto
  grouping Status {
    container Status_DeviceStatus {
      uses monitorpb:DeviceStatus;
    }
    container Status_SystemStatus {
      uses monitorpb:SystemStatus;
    }
    container Status_LedStatus {
      uses monitorpb:LEDStatus;
    }
  }
  // core/monitor/monitor.proto
  grouping DeviceStatusEntry {
    leaf DeviceStatusEntry_MonitorOption {
      type monitorpb:DeviceMonitorTypeOptions;
    }
    container DeviceStatusEntry_Value {
      uses monitorpb:DisplayValue;
    }
    leaf DeviceStatusEntry_LoggingOption {
      type eventpb:LoggingTypeOptions;
    }
  }
  // core/monitor/monitor.proto
  grouping DeviceStatus {
    container DeviceStatus_List {
      uses monitorpb:DeviceStatusEntry;
    }
  }
  // core/monitor/monitor.proto
  grouping SystemStatusEntry {
    leaf SystemStatusEntry_MonitorOption {
      type monitorpb:SystemMonitorTypeOptions;
    }
    container SystemStatusEntry_Value {
      uses monitorpb:DisplayValue;
    }
    leaf SystemStatusEntry_LoggingOption {
      type eventpb:LoggingTypeOptions;
    }
  }
  // core/monitor/monitor.proto
  grouping SystemStatus {
    container SystemStatus_List {
      uses monitorpb:SystemStatusEntry;
    }
  }
  // core/monitor/monitor.proto
  grouping DisplayValue {
    leaf DisplayValue_ValueUnit {
      type string;
    }
    leaf DisplayValue_IntValue {
      type int32;
    }
    leaf DisplayValue_FloatValue {
      type decimal64 {
        fraction-digits 2;
      }
    }
    leaf DisplayValue_Int64Value {
      type int64;
    }
    leaf DisplayValue_Float64Value {
      type decimal64 {
        fraction-digits 2;
      }
    }
  }
  // core/monitor/monitor.proto
  grouping LEDStatus {
    container LEDStatus_SystemList {
      uses monitorpb:SystemLEDStatusEntry;
    }
    container LEDStatus_PortList {
      uses monitorpb:PortLEDStatusEntry;
    }
  }
  // core/monitor/monitor.proto
  grouping SystemLEDStatusEntry {
    leaf SystemLEDStatusEntry_LedType {
      type monitorpb:HardwareLEDTypeOptions;
    }
    container SystemLEDStatusEntry_LedState {
      uses monitorpb:LEDStateEntry;
    }
  }
  // core/monitor/monitor.proto
  grouping PortLEDStatusEntry {
    container PortLEDStatusEntry_IdentifyNo {
      uses devicepb:InterfaceIdentify;
    }
    leaf PortLEDStatusEntry_IsSfp {
      type boolean;
    }
    container PortLEDStatusEntry_LinkLedState {
      uses monitorpb:LEDStateEntry;
    }
    leaf PortLEDStatusEntry_IsSupportPoELed {
      type boolean;
    }
    container PortLEDStatusEntry_PoELedState {
      uses monitorpb:LEDStateEntry;
    }
    leaf PortLEDStatusEntry_IsSupportSpeedLed {
      type boolean;
    }
    container PortLEDStatusEntry_SpeedLedState {
      uses monitorpb:LEDStateEntry;
    }
  }
  // core/monitor/monitor.proto
  grouping LEDStateEntry {
    leaf LEDStateEntry_StateOption {
      type monitorpb:LEDStateTypeOptions;
    }
    leaf LEDStateEntry_ColorOption {
      type monitorpb:LEDColorTypeOptions;
    }
    leaf LEDStateEntry_BlinkingIntervalMs {
      type int32;
    }
  }
}
