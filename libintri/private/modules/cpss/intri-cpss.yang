module intri-cpss {
  namespace "intri:intri-cpss";
  prefix "intri-cpss";
  import cpsspb {
    prefix "cpsspb";
  }
  organization "Intrising Inc.";
  contact "xxx@intrising.com.tw";
  revision 2022-06-14 {
    description "Build date.";
  }
}
