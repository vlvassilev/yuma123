// Code generated by protoc-gen-yang. DO NOT EDIT.


/* ****************************************************************************************************
 * Import Path : "github.com/Intrising/intri-type/core/mirroring"                                     *
 * Dir Path    : github.com/Intrising/intri-type/core/mirroring                                       *
 * Go Package  : mirroring                                                                            *
 * Files       : 2                                                                                    *
 **************************************************************************************************** */
module intri-mirroring {

  namespace "intri:intri-mirroring";

  prefix "intri-mirroring";

  organization "Intrising Inc.";

  contact "intrising@intrising.com.tw";

  revision 2022-06-23 {
    description "Build date.";
  }

  import intri-device {
    prefix intri-device;
  }
  import intri-empty {
    prefix intri-empty;
  }
  import intri-common {
    prefix intri-common;
  }


  /* **************************************************************************************************
   * Enums       : 3                                                                                  *
   ************************************************************************************************** */
  /* core/mirroring/mirroring.proto */
  typedef DestinationTypeOptions {
    type enumeration {
      enum DESTINATION_TYPE_LOCAL {
        description "[Local] to set SPAN(Local Switched Port Analyzer) destination port interface";
        value 0;
      }
      enum DESTINATION_TYPE_REMOTE {
        description "[Remote] to set RSPAN(Remote SPAN) VLAN";
        value 1;
      }
    }
  }
  /* core/mirroring/mirroring.proto */
  typedef SourceInterfaceTypeOptions {
    type enumeration {
      enum SOURCE_INTERFACE_TYPE_LOCAL {
        description "[Local] to set SPAN(Local Switched Port Analyzer) source port interface";
        value 0;
      }
      enum SOURCE_INTERFACE_TYPE_VLAN {
        description "*[Internal] to set source port interface";
        value 1;
      }
      enum SOURCE_INTERFACE_TYPE_REMOTE {
        description "[Remote] to set RSPAN(Remote SPAN) VLAN";
        value 2;
      }
    }
  }
  /* core/mirroring/mirroring.proto */
  typedef DirectionTypeOptions {
    type enumeration {
      enum MIRRORING_DIRECTION_TYPE_NONE {
        description "[None] to disable mirroring direction";
        value 0;
      }
      enum MIRRORING_DIRECTION_TYPE_TX_ONLY {
        description "[TX only] to set mirroring direction TX only";
        value 1;
      }
      enum MIRRORING_DIRECTION_TYPE_RX_ONLY {
        description "[RX only] to set mirroring direction RX only";
        value 2;
      }
      enum MIRRORING_DIRECTION_TYPE_BOTH {
        description "[TX+RX] to set mirroring direction TX and RX both";
        value 3;
      }
    }
  }


  /* **************************************************************************************************
   * Msgs        : 6                                                                                  *
   ************************************************************************************************** */
  /* core/mirroring/mirroring.proto */
  grouping Config {
    container RSPAN {
      uses RSPANConfig;
    }
    container DestinationList {
      uses DestinationSession;
    }
    container SourceList {
      uses SourceSession;
    }
  }
  /* core/mirroring/mirroring.proto */
  grouping DestinationSessionEntry {
    leaf Index {
      type int32;
    }
    leaf Type {
      type DestinationTypeOptions;
    }
    container IdentifyNo {
      uses intri-device:InterfaceIdentify;
    }
  }
  /* core/mirroring/mirroring.proto */
  grouping DestinationSession {
    container List {
      list List_Entry {
        uses DestinationSessionEntry;
      }
    }
  }
  /* core/mirroring/mirroring.proto */
  grouping SourceSessionEntry {
    leaf DestinationIndex {
      type int32;
    }
    leaf SourceInterface {
      type SourceInterfaceTypeOptions;
    }
    container IdentifyNo {
      uses intri-device:InterfaceIdentify;
    }
    leaf DirectionType {
      type DirectionTypeOptions;
    }
  }
  /* core/mirroring/mirroring.proto */
  grouping SourceSession {
    container List {
      list List_Entry {
        uses SourceSessionEntry;
      }
    }
  }
  /* core/mirroring/mirroring.proto */
  grouping RSPANConfig {
    leaf Enabled {
      type boolean;
    }
    leaf VlanID {
      type int32;
    }
  }


  /* **************************************************************************************************
   * Services    : 1                                                                                  *
   ************************************************************************************************** */

  /* **************************************************************************************************
   * Service     : Mirroring                                                                          *
   * Methods     : 11                                                                                 *
   ************************************************************************************************** */
  /* core/mirroring/service.proto */
  rpc intri-mirroring-GetConfig {
    output  {
      uses Config;
    }
  }
  /* core/mirroring/service.proto */
  rpc intri-mirroring-GetRSPAN {
    output  {
      uses RSPANConfig;
    }
  }
  /* core/mirroring/service.proto */
  rpc intri-mirroring-SetRSPAN {
    input  {
      uses RSPANConfig;
    }
  }
  /* core/mirroring/service.proto */
  rpc intri-mirroring-GetDestinationList {
    output  {
      uses DestinationSession;
    }
  }
  /* core/mirroring/service.proto */
  rpc intri-mirroring-AddDestination {
    input  {
      uses DestinationSessionEntry;
    }
  }
  /* core/mirroring/service.proto */
  rpc intri-mirroring-DeleteDestination {
    input  {
      uses intri-common:Index;
    }
  }
  /* core/mirroring/service.proto */
  rpc intri-mirroring-UpdateDestination {
    input  {
      uses DestinationSessionEntry;
    }
  }
  /* core/mirroring/service.proto */
  rpc intri-mirroring-GetSourceList {
    output  {
      uses SourceSession;
    }
  }
  /* core/mirroring/service.proto */
  rpc intri-mirroring-AddSource {
    input  {
      uses SourceSessionEntry;
    }
  }
  /* core/mirroring/service.proto */
  rpc intri-mirroring-DeleteSource {
    input  {
      uses SourceSessionEntry;
    }
  }
  /* core/mirroring/service.proto */
  rpc intri-mirroring-UpdateSource {
    input  {
      uses SourceSessionEntry;
    }
  }

}
