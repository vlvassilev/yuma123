// Code generated by protoc-gen-yang. DO NOT EDIT.


/* ****************************************************************************************************
 * Import Path : "github.com/golang/protobuf/ptypes/duration"                                         *
 * Dir Path    : github.com/golang/protobuf/ptypes/duration                                           *
 * Go Package  : duration                                                                             *
 * Files       : 1                                                                                    *
 **************************************************************************************************** */
module intri-duration {

  namespace "intri:intri-duration";

  prefix "intri-duration";

  organization "Intrising Inc.";

  contact "intrising@intrising.com.tw";

  revision 2022-06-23 {
    description "Build date.";
  }


  /* **************************************************************************************************
   * Msgs        : 1                                                                                  *
   ************************************************************************************************** */
  /* google/protobuf/duration.proto */
  grouping Duration {
    leaf Seconds {
      type int64;
    }
    leaf Nanos {
      type int32;
    }
  }

}
