submodule intri-mirroring-msg {
  belongs-to "intri-mirroring" {
    prefix "intri-mirroring-msg";
  }
  include intri-mirroring-enum;
  import mirroringpb {
    prefix "mirroringpb";
  }
  import devicepb {
    prefix "devicepb";
  }
  revision 2022-06-14 {
    description "Build date.";
  }
  // core/mirroring/mirroring.proto
  grouping Config {
    container Config_RSPAN {
      uses mirroringpb:RSPANConfig;
    }
    container Config_DestinationList {
      uses mirroringpb:DestinationSession;
    }
    container Config_SourceList {
      uses mirroringpb:SourceSession;
    }
  }
  // core/mirroring/mirroring.proto
  grouping DestinationSessionEntry {
    leaf DestinationSessionEntry_Index {
      type int32;
    }
    leaf DestinationSessionEntry_Type {
      type mirroringpb:DestinationTypeOptions;
    }
    container DestinationSessionEntry_IdentifyNo {
      uses devicepb:InterfaceIdentify;
    }
  }
  // core/mirroring/mirroring.proto
  grouping DestinationSession {
    container DestinationSession_List {
      uses mirroringpb:DestinationSessionEntry;
    }
  }
  // core/mirroring/mirroring.proto
  grouping SourceSessionEntry {
    leaf SourceSessionEntry_DestinationIndex {
      type int32;
    }
    leaf SourceSessionEntry_SourceInterface {
      type mirroringpb:SourceInterfaceTypeOptions;
    }
    container SourceSessionEntry_IdentifyNo {
      uses devicepb:InterfaceIdentify;
    }
    leaf SourceSessionEntry_DirectionType {
      type mirroringpb:DirectionTypeOptions;
    }
  }
  // core/mirroring/mirroring.proto
  grouping SourceSession {
    container SourceSession_List {
      uses mirroringpb:SourceSessionEntry;
    }
  }
  // core/mirroring/mirroring.proto
  grouping RSPANConfig {
    leaf RSPANConfig_Enabled {
      type boolean;
    }
    leaf RSPANConfig_VlanID {
      type int32;
    }
  }
}
