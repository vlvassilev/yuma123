// Code generated by protoc-gen-yang. DO NOT EDIT.


/* ****************************************************************************************************
 * Import Path : "github.com/Intrising/intri-type/core/userinterface"                                 *
 * Dir Path    : github.com/Intrising/intri-type/core/userinterface                                   *
 * Go Package  : userinterface                                                                        *
 * Files       : 6                                                                                    *
 **************************************************************************************************** */
module intri-userinterface {

  namespace "intri:intri-userinterface";

  prefix "intri-userinterface";

  organization "Intrising Inc.";

  contact "intrising@intrising.com.tw";

  revision 2022-06-23 {
    description "Build date.";
  }

  import intri-empty {
    prefix intri-empty;
  }
  import intri-common {
    prefix intri-common;
  }


  /* **************************************************************************************************
   * Enums       : 2                                                                                  *
   ************************************************************************************************** */
  /* core/userinterface/snmp.proto */
  typedef SNMPV3ConfigSecurityModelTypeOptions {
    type enumeration {
      enum SNMP_V3_CONFIG_SECURITY_MODEL_USM {
        description "[USM] Assign the USM as the SNMPv3 security model";
        value 0;
      }
      enum SNMP_V3_CONFIG_SECURITY_MODEL_VACM {
        description "[VCAM] Assign the VACM as the SNMPv3 security model";
        value 1;
      }
      enum SNMP_V3_CONFIG_SECURITY_MODEL_TSM {
        description "[TSM] Assign the TSM as the SNMPv3 security model";
        value 2;
      }
    }
  }
  /* core/userinterface/web.proto */
  typedef WebProtocolTypeOptions {
    type enumeration {
      enum WEB_PROTOCOL_TYPE_DISABLED {
        description "[Disabled] Web interface is disabled";
        value 0;
      }
      enum WEB_PROTOCOL_TYPE_HTTP_UNSECURE {
        description "[HTTP Only] Standard client interface";
        value 1;
      }
      enum WEB_PROTOCOL_TYPE_HTTPS_SECURE {
        description "[HTTPS Only] Secure client interface";
        value 2;
      }
      enum WEB_PROTOCOL_TYPE_HTTP_AND_HTTPS {
        description "[HTTP & HTTPS] Both Standard & Secure client interface";
        value 3;
      }
    }
  }


  /* **************************************************************************************************
   * Msgs        : 4                                                                                  *
   ************************************************************************************************** */
  /* core/userinterface/cli.proto */
  grouping CLIConfig {
    leaf TelnetEnabled {
      type boolean;
    }
    leaf SSHEnabled {
      type boolean;
    }
    leaf WelcomeMessage {
      type string;
    }
    leaf InactivityTimeout {
      type int32;
    }
  }
  /* core/userinterface/snmp.proto */
  grouping SNMPConfig {
    leaf SNMPV1Enabled {
      type boolean;
    }
    leaf SNMPV2CEnabled {
      type boolean;
    }
    leaf GetCommunity {
      type string;
    }
    leaf SetCommunity {
      type string;
    }
    leaf SNMPV1V2Username {
      type string;
    }
    leaf PermitV1V2SetCommands {
      type boolean;
    }
    leaf SNMPV3Enabled {
      type boolean;
    }
    leaf SecurityModel {
      type SNMPV3ConfigSecurityModelTypeOptions;
    }
    leaf SNMPEngineID {
      type string;
    }
    leaf TrapEngineID {
      type string;
    }
  }
  /* core/userinterface/web.proto */
  grouping WebConfig {
    leaf Protocol {
      type WebProtocolTypeOptions;
    }
    leaf WebTimeout {
      type int32;
    }
    leaf HTTPPort {
      type int32;
    }
    leaf HTTPSPort {
      type int32;
    }
    leaf EncryptedCertPassphrase {
      type string;
    }
    leaf LoginMessage {
      type string;
    }
  }
  /* core/userinterface/userinterface.proto */
  grouping Config {
    container Cli {
      uses CLIConfig;
    }
    container Snmp {
      uses SNMPConfig;
    }
    container Web {
      uses WebConfig;
    }
  }


  /* **************************************************************************************************
   * Services    : 1                                                                                  *
   ************************************************************************************************** */

  /* **************************************************************************************************
   * Service     : UserInterface                                                                      *
   * Methods     : 9                                                                                  *
   ************************************************************************************************** */
  /* core/userinterface/service.proto */
  rpc intri-userinterface-GetConfig {
    output  {
      uses Config;
    }
  }
  /* core/userinterface/service.proto */
  rpc intri-userinterface-GetCLIConfig {
    output  {
      uses CLIConfig;
    }
  }
  /* core/userinterface/service.proto */
  rpc intri-userinterface-SetCLIConfig {
    input  {
      uses CLIConfig;
    }
  }
  /* core/userinterface/service.proto */
  rpc intri-userinterface-GetWebConfig {
    output  {
      uses WebConfig;
    }
  }
  /* core/userinterface/service.proto */
  rpc intri-userinterface-SetWebConfig {
    input  {
      uses WebConfig;
    }
  }
  /* core/userinterface/service.proto */
  rpc intri-userinterface-RunRestartWebServer {
    input  {
      uses intri-common:Confirm;
    }
  }
  /* core/userinterface/service.proto */
  rpc intri-userinterface-GetSNMPConfig {
    output  {
      uses SNMPConfig;
    }
  }
  /* core/userinterface/service.proto */
  rpc intri-userinterface-SetSNMPConfig {
    input  {
      uses SNMPConfig;
    }
  }
  /* core/userinterface/service.proto */
  rpc intri-userinterface-RunRestartSNMPServer {
    input  {
      uses intri-common:Confirm;
    }
  }

}
