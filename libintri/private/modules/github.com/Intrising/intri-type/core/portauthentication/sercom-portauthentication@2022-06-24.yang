module sercom-portauthentication {

  namespace "sercom:sercom-portauthentication";
  prefix "sercom-portauthentication";
  organization "
    Sercomm Inc.";
  contact "
    sercomm@sercomm.com.tw";
  revision 2022-06-24 {
    description "Build date.";
  }

  import sercom-device {
    prefix sercom-device;
  }
  import sercom-empty {
    prefix sercom-empty;
  }
  import sercom-common {
    prefix sercom-common;
  }
  typedef AuthorizationStateTypeOptions {
    type enumeration {
      enum AUTHORIZATION_STATE_TYPE_UNDEFINED {
        description "[Undefined]";
        value 0;
      }
      enum AUTHORIZATION_STATE_TYPE_DISABLED {
        description "[Disabled]";
        value 1;
      }
      enum AUTHORIZATION_STATE_TYPE_UNAUTHORIZED {
        description "[Unauthorized]";
        value 2;
      }
      enum AUTHORIZATION_STATE_TYPE_PROCESSING {
        description "[Processing]";
        value 3;
      }
      enum AUTHORIZATION_STATE_TYPE_AUTHORIZED {
        description "[Authorized]";
        value 4;
      }
      enum AUTHORIZATION_STATE_TYPE_REJECTED {
        description "[Rejected]";
        value 5;
      }
    }
  }
  typedef AuthorizationModeTypeOptions {
    type enumeration {
      enum AUTHORIZATION_MODE_TYPE_ALWAYSAUTH {
        description "[Always Auth]";
        value 0;
      }
      enum AUTHORIZATION_MODE_TYPE_FORCEUNAUTH {
        description "[Force Unauth]";
        value 1;
      }
      enum AUTHORIZATION_MODE_TYPE_VIAMACTABLE {
        description "[Via MAC Table]";
        value 2;
      }
      enum AUTHORIZATION_MODE_TYPE_MACVIARADIUS {
        description "[MAC via RADIUS]";
        value 3;
      }
      enum AUTHORIZATION_MODE_TYPE_8021XVIARADIUS {
        description "[802.1X via RADIUS]";
        value 4;
      }
      enum AUTHORIZATION_MODE_TYPE_MAC8021XVIARADIUS {
        description "[MAC 802.1X via RADIUS]";
        value 5;
      }
      enum AUTHORIZATION_MODE_TYPE_8021XMACVIARADIUS {
        description "[802.1X MAC via RADIUS]";
        value 6;
      }
      enum AUTHORIZATION_MODE_TYPE_NONE {
        description "*internal";
        value 9;
      }
    }
  }
  typedef UnAuthorizationModeTypeOptions {
    type enumeration {
      enum UNAUTHORIZATION_MODE_TYPE_BLOCKED {
        description "[Blocked]";
        value 0;
      }
      enum UNAUTHORIZATION_MODE_TYPE_USE_UNAUTHORIZEDVLAN {
        description "[Use Unauthorized VLAN]";
        value 1;
      }
      enum UNAUTHORIZATION_MODE_TYPE_INCOMING_BLOCKED {
        description "[Incoming Blocked]";
        value 2;
      }
    }
  }
  typedef MACSpellingTypeOptions {
    type enumeration {
      enum MAC_SPELLING_TYPE_LOWERCASE {
        description "[Lowercase]";
        value 0;
      }
      enum MAC_SPELLING_TYPE_UPPERCASE {
        description "[Uppercase]";
        value 1;
      }
    }
  }
  typedef MACPasswordSourceTypeOptions {
    type enumeration {
      enum MAC_PASSWORD_SOURCE_TYPE_USEMAC {
        description "[Use MAC]";
        value 0;
      }
      enum MAC_PASSWORD_SOURCE_TYPE_USEPASSWORD {
        description "[Use Password]";
        value 1;
      }
    }
  }
  typedef EntryStateTypeOptions {
    type enumeration {
      enum ENTRY_STATE_TYPE_UNUSED {
        description "[Unused]";
        value 0;
      }
      enum ENTRY_STATE_TYPE_INACTIVE {
        description "[Inactive]";
        value 1;
      }
      enum ENTRY_STATE_TYPE_ACTIVE {
        description "[Active]";
        value 2;
      }
    }
  }
  typedef MACTimeoutTypeOptions {
    type enumeration {
      enum MAC_TIMEOUT_TYPE_NONE {
        description "[None]";
        value 0;
      }
      enum MAC_TIMEOUT_TYPE_SLOW {
        description "[Slow]";
        value 1;
      }
    }
  }
  grouping Config {
    container SystemConfig {
      uses SystemConfig;
    }
    container PortConfig {
      uses PortConfig;
    }
    container AuthorizedMACs {
      uses AuthorizedMACs;
    }
  }
  grouping AuthorizedMACsEntry {
    leaf Name {
      mandatory "true";
      type string;
    }
    leaf MACAddress {
      mandatory "true";
      type string;
    }
    container PermittedPortList {
      list PermittedPortList_Entry {
        uses sercom-device:InterfaceIdentify;
      }
    }
    leaf TreatAsVendorMAC {
      mandatory "true";
      type boolean;
    }
  }
  grouping AuthorizedMACs {
    container List {
      list List_Entry {
        uses AuthorizedMACsEntry;
      }
    }
  }
  grouping SystemConfig {
    leaf PortAccessControlEnabled {
      mandatory "true";
      type boolean;
    }
    leaf ReauthenticationPeriod {
      mandatory "true";
      type int32;
    }
    leaf NASIdentifier {
      mandatory "true";
      type string;
    }
    leaf MACSeparatorChar {
      mandatory "true";
      type string;
    }
    leaf MACSpelling {
      mandatory "true";
      type MACSpellingTypeOptions;
    }
    leaf MACPasswordSource {
      mandatory "true";
      type MACPasswordSourceTypeOptions;
    }
    leaf MACPasswordString {
      mandatory "true";
      type string;
    }
    leaf PrimaryAuthServerName {
      mandatory "true";
      type string;
    }
    leaf PrimaryAcctServerName {
      mandatory "true";
      type string;
    }
    leaf FallbackAuthServerName {
      mandatory "true";
      type string;
    }
    leaf FallbackAcctServerName {
      mandatory "true";
      type string;
    }
    leaf ServerDownTimeout {
      mandatory "true";
      type int32;
    }
  }
  grouping PortConfig {
    container List {
      list List_Entry {
        uses PortConfigEntry;
      }
    }
  }
  grouping PortConfigEntry {
    container IdentifyNo {
      uses sercom-device:InterfaceIdentify;
    }
    leaf AuthorizedMode {
      mandatory "true";
      type AuthorizationModeTypeOptions;
    }
    leaf UnAuthorizedMode {
      mandatory "true";
      type UnAuthorizationModeTypeOptions;
    }
    leaf AuthFailRetryInterval {
      mandatory "true";
      type int32;
    }
    leaf LimitedNumberOfMACs {
      mandatory "true";
      type int32;
    }
    leaf MACTimeout {
      mandatory "true";
      type MACTimeoutTypeOptions;
    }
  }
  grouping PortStatus {
    container List {
      list List_Entry {
        uses PortStatusEntry;
      }
    }
  }
  grouping PortStatusEntry {
    container IdentifyNo {
      uses sercom-device:InterfaceIdentify;
    }
    leaf AuthorizationState {
      mandatory "true";
      type AuthorizationStateTypeOptions;
    }
    leaf AuthorizationMode {
      mandatory "true";
      type AuthorizationModeTypeOptions;
    }
    leaf LastStateChange {
      mandatory "true";
      type string;
    }
    leaf NumberOfMACsToLearn {
      mandatory "true";
      type int32;
    }
    leaf NumberOfLearnedMACs {
      mandatory "true";
      type int32;
    }
  }
  grouping PortAuthorizationStatus {
    container List {
      list List_Entry {
        uses PortAuthorizationStatusEntry;
      }
    }
  }
  grouping PortAuthorizationStatusEntry {
    container IdentifyNo {
      uses sercom-device:InterfaceIdentify;
    }
    leaf AuthorizationState {
      mandatory "true";
      type AuthorizationStateTypeOptions;
    }
    leaf UserMAC {
      mandatory "true";
      type string;
    }
    leaf UserName {
      mandatory "true";
      type string;
    }
    leaf IdleTimeout {
      mandatory "true";
      type int32;
    }
    leaf SessionTimeout {
      mandatory "true";
      type int32;
    }
    leaf LastStateChange {
      mandatory "true";
      type string;
    }
  }
  grouping UserStatus {
    container List {
      list List_Entry {
        uses UserStatusEntry;
      }
    }
  }
  grouping UserStatusEntry {
    leaf EntryState {
      mandatory "true";
      type EntryStateTypeOptions;
    }
    leaf AuthorizationState {
      mandatory "true";
      type AuthorizationStateTypeOptions;
    }
    leaf AuthorizationMode {
      mandatory "true";
      type AuthorizationModeTypeOptions;
    }
    container IdentifyNo {
      uses sercom-device:InterfaceIdentify;
    }
    leaf UserMAC {
      mandatory "true";
      type string;
    }
    leaf UserName {
      mandatory "true";
      type string;
    }
    leaf VlanID {
      mandatory "true";
      type int32;
    }
    leaf IdleTimeout {
      mandatory "true";
      type int32;
    }
    leaf SessionTimeout {
      mandatory "true";
      type int32;
    }
    leaf LoginTimeStamp {
      mandatory "true";
      type string;
    }
  }
  grouping LearnMACNowEntry {
    container IdentifyNo {
      uses sercom-device:InterfaceIdentify;
    }
    leaf Amount {
      mandatory "true";
      type int32;
    }
  }
  grouping UnauthorizeMACEntry {
    container IdentifyNo {
      uses sercom-device:InterfaceIdentify;
    }
    leaf MACAddress {
      mandatory "true";
      type string;
    }
  }
  rpc sercom-portauthentication-PortAuthentication-GetConfig {
    output {
      uses Config;
    }
  }
  rpc sercom-portauthentication-PortAuthentication-GetSystemConfig {
    output {
      uses SystemConfig;
    }
  }
  rpc sercom-portauthentication-PortAuthentication-SetSystemConfig {
    input {
      uses SystemConfig;
    }
  }
  rpc sercom-portauthentication-PortAuthentication-GetPortConfig {
    output {
      uses PortConfig;
    }
  }
  rpc sercom-portauthentication-PortAuthentication-UpdatePortConfig {
    input {
      uses PortConfig;
    }
  }
  rpc sercom-portauthentication-PortAuthentication-GetAuthorizedMACsConfig {
    output {
      uses AuthorizedMACs;
    }
  }
  rpc sercom-portauthentication-PortAuthentication-AddAuthorizedMACsEntryConfig {
    input {
      uses AuthorizedMACsEntry;
    }
  }
  rpc sercom-portauthentication-PortAuthentication-DeleteAuthorizedMACsEntryConfig {
    input {
      uses sercom-common:Name;
    }
  }
  rpc sercom-portauthentication-PortAuthentication-UpdateAuthorizedMACsEntryConfig {
    input {
      uses AuthorizedMACsEntry;
    }
  }
  rpc sercom-portauthentication-PortAuthentication-GetPortStatus {
    output {
      uses PortStatus;
    }
  }
  rpc sercom-portauthentication-PortAuthentication-GetMACAuthorizationStatus {
    output {
      uses PortAuthorizationStatus;
    }
  }
  rpc sercom-portauthentication-PortAuthentication-Get8021XAuthorizationStatus {
    output {
      uses PortAuthorizationStatus;
    }
  }
  rpc sercom-portauthentication-PortAuthentication-GetUserStatus {
    output {
      uses UserStatus;
    }
  }
  rpc sercom-portauthentication-PortAuthentication-RunPortConfigLearnMACNow {
    input {
      uses LearnMACNowEntry;
    }
  }
  rpc sercom-portauthentication-PortAuthentication-RunPortConfigReauthenticate {
    input {
      uses sercom-device:InterfaceIdentify;
    }
  }
  rpc sercom-portauthentication-PortAuthentication-RunPortConfigUnauthorizeMAC {
    input {
      uses UnauthorizeMACEntry;
    }
  }
}
